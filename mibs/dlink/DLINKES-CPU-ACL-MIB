--  *****************************************************************
--  DLINKES-CPU-ACL-MIB.mib : CPU ACL MIB
-- 
--  Copyright (c) 2014 D-Link Corporation, all rights reserved.
--   
--  *****************************************************************
DLINKES-CPU-ACL-MIB DEFINITIONS ::= BEGIN


    IMPORTS
        MODULE-IDENTITY,
        OBJECT-TYPE
            FROM SNMPv2-SMI
        DisplayString,
        RowStatus
            FROM SNMPv2-TC
        MODULE-COMPLIANCE,
	OBJECT-GROUP
	    FROM SNMPv2-CONF
        PortList
            FROM Q-BRIDGE-MIB                                                
        dlinkCommon
            FROM DLINK-ID-REC-MIB;


    dlinkEsCPUAclMIB MODULE-IDENTITY
        LAST-UPDATED "201407230000Z"
        ORGANIZATION "D-Link Corp."
        CONTACT-INFO
            "        D-Link Corporation
             Postal: No. 289, Sinhu 3rd Rd., Neihu District,
             Taipei City 114, Taiwan, R.O.C
             Tel:     +886-2-66000123
             E-mail: tsd@dlink.com.tw
            "
        DESCRIPTION
                "The Structure of software Access Control List Information for the
                 proprietary enterprise."
	
	    REVISION "201407230000Z"
        DESCRIPTION
            "Move the compiler warning for node esCPUAclMIBCompliances."         

        REVISION "201405120000Z"
        DESCRIPTION
            "This is the first version of the MIB file for 'CPU ACL' functionality."         
        ::= { dlinkCommon 178 }

-- -----------------------------------------------------------------------------
--	MIB OBJECTS     
-- -----------------------------------------------------------------------------

	esCPUAclMIBNotifications	OBJECT IDENTIFIER ::= { dlinkEsCPUAclMIB 0 }
	esCPUAclMIBObjects 		OBJECT IDENTIFIER ::= { dlinkEsCPUAclMIB 1 }
	esCPUAclMIBConformance	OBJECT IDENTIFIER ::= { dlinkEsCPUAclMIB 2 } 

-- -----------------------------------------------------------------------------     
    esCPUAclFilter              OBJECT IDENTIFIER ::= { esCPUAclMIBObjects 1 }

    esCPUAclFilterMapTable OBJECT-TYPE
        SYNTAX          SEQUENCE OF EsCPUAclFilterMapEntry
        MAX-ACCESS      not-accessible
        STATUS          current
        DESCRIPTION
            "The table contains information about CPU ACL filter map."
        ::= { esCPUAclFilter 1 }

    esCPUAclFilterMapEntry OBJECT-TYPE
        SYNTAX          EsCPUAclFilterMapEntry
        MAX-ACCESS      not-accessible
        STATUS          current
        DESCRIPTION
            "An entry defined in esCPUAclFilterMapTable. An entry is 
            created/removed when an CPU ACL filter map is created/deleted."
        INDEX { esCPUAclFilterMapName }
        ::= { esCPUAclFilterMapTable 1 }

    EsCPUAclFilterMapEntry ::= SEQUENCE {
        esCPUAclFilterMapName		DisplayString,
        esCPUAclFilterMapRowStatus	RowStatus,
        esCPUAclFilterMapApplyInterfaces	PortList    
    }

    esCPUAclFilterMapName OBJECT-TYPE
        SYNTAX          DisplayString (SIZE (1..32))
        MAX-ACCESS      not-accessible
        STATUS          current
        DESCRIPTION
            "The name of the CPU ACL filter map."
        ::= { esCPUAclFilterMapEntry 1 }

    esCPUAclFilterMapRowStatus OBJECT-TYPE
        SYNTAX      RowStatus
        MAX-ACCESS  read-create
        STATUS      current
        DESCRIPTION
            "This object allows the dynamic creation and deletion of a CPU ACL filter map."
        ::= { esCPUAclFilterMapEntry 2 }                     
        
    esCPUAclFilterMapApplyInterfaces OBJECT-TYPE
        SYNTAX          PortList
        MAX-ACCESS      read-create
        STATUS          current
        DESCRIPTION
            "Indicates the physical interface(s)for specify CPU ACL filter map.
            An interface can be configured to at most one filter map. 
            When you configure an interface to a new filter map, the interface 
            will be removed from the previous filter map."
        ::= { esCPUAclFilterMapEntry 3 }
-- -----------------------------------------------------------------------------
    esCPUAclFilterMapMatchTable OBJECT-TYPE
        SYNTAX          SEQUENCE OF EsCPUAclFilterMapMatchEntry
        MAX-ACCESS      not-accessible
        STATUS          current
        DESCRIPTION
            "The table represents a list of CUP ACL filter group configuration."
        ::= { esCPUAclFilter 2 }

    esCPUAclFilterMapMatchEntry OBJECT-TYPE
        SYNTAX          EsCPUAclFilterMapMatchEntry
        MAX-ACCESS  not-accessible
        STATUS      current
        DESCRIPTION
            "The table represents a CPU ACL filter group configuration."
        INDEX { esCPUAclFilterMapName, esCPUAclFilterMapMatchName }
        ::= { esCPUAclFilterMapMatchTable 1 }

    EsCPUAclFilterMapMatchEntry ::= SEQUENCE {
        esCPUAclFilterMapMatchName		DisplayString,   
        esCPUAclFilterMapMatchRowStatus		RowStatus,
        esCPUAclFilterMapMatchSN			INTEGER,
        esCPUAclFilterMapMatchType		INTEGER
    }

    esCPUAclFilterMapMatchName OBJECT-TYPE
        SYNTAX          DisplayString (SIZE (1..32))
        MAX-ACCESS      not-accessible
        STATUS          current
        DESCRIPTION
            "This object indicates the name of access-list will be associated."
        ::= { esCPUAclFilterMapMatchEntry 1 }
    
    esCPUAclFilterMapMatchRowStatus OBJECT-TYPE
        SYNTAX      RowStatus
        MAX-ACCESS  read-create
        STATUS      current
        DESCRIPTION
            "The row status variable, used according to installation
            and removal conventions for conceptual rows."
        ::= { esCPUAclFilterMapMatchEntry 2 }

     esCPUAclFilterMapMatchSN OBJECT-TYPE
        SYNTAX          INTEGER ( 1..65535 )
        MAX-ACCESS      read-create
        STATUS          current
        DESCRIPTION
            "Indicates the sequence number of a ACL filter rule. 
             The value range is 1 to 65535.             
             The lower the number is, the higher the priority of the access-list.
             "
        ::= { esCPUAclFilterMapMatchEntry 3 }
    
    esCPUAclFilterMapMatchType OBJECT-TYPE
        SYNTAX		INTEGER {
			expert(1), 
			mac(2),
			ip(3),
			ipv6(4)
			}
        MAX-ACCESS      read-create
        STATUS          current
        DESCRIPTION
            "This object indicates the type of MAC/IP/IPv6/expert access-list 
            which will be associated.
            If the match entrys with same sequence number defined by esCPUAclFilterMapMatchSN,
            they are processed in the order: expert access-list, mac access-list, ip access-list, ipv6 access-list."
        ::= { esCPUAclFilterMapMatchEntry 4 }

--  ***************************************************************************	
--  Conformance
--  ***************************************************************************			   		
    esCPUAclMIBCompliances  OBJECT IDENTIFIER ::= { esCPUAclMIBConformance 1 }
    esCPUAclMIBGroups  OBJECT IDENTIFIER         ::= { esCPUAclMIBConformance 2 }

    esCPUAclCompliance MODULE-COMPLIANCE
        STATUS          current
        DESCRIPTION
            "The compliance statement for entities which implement the
			DLINKES-CPU-ACL-MIB."		
			
        MODULE          -- this module
        MANDATORY-GROUPS    {
            esCPUAclFilterGroup
        }  

        GROUP esCPUAclFilterInterfaceGroup
        DESCRIPTION
            "This group is required only if the CPU acl interface
              is implemented by the agent."

        ::= { esCPUAclMIBCompliances 1 }


-- Units of Conformance

    esCPUAclFilterGroup OBJECT-GROUP
		OBJECTS {
        esCPUAclFilterMapRowStatus,esCPUAclFilterMapMatchType,
        esCPUAclFilterMapMatchSN,esCPUAclFilterMapMatchRowStatus
		}
		STATUS current
		DESCRIPTION
			"A collection of objects provides basic management and information
            for CPU acl feature."
		::= { esCPUAclMIBGroups 1 }
		

     esCPUAclFilterInterfaceGroup OBJECT-GROUP
		OBJECTS {
        esCPUAclFilterMapApplyInterfaces
        }
		STATUS current
		DESCRIPTION
			"A collection of objects providing general CPU acl interface configuration."
		::= { esCPUAclMIBGroups 2 }


END
