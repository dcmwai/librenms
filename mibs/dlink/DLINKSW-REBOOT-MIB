--  *****************************************************************
--  DLINKSW-REBOOTSCHEDULE-MIB.mib : REBOOTSCHEDULE MIB
--
--  Copyright (c) 2014 D-Link Corporation, all rights reserved.
--
--  *****************************************************************
DLINKSW-REBOOT-MIB DEFINITIONS ::= BEGIN

    IMPORTS
        MODULE-IDENTITY, NOTIFICATION-TYPE,
        OBJECT-TYPE, Integer32, Unsigned32
                    FROM SNMPv2-SMI
        RowStatus
                    FROM SNMPv2-TC
        MODULE-COMPLIANCE, OBJECT-GROUP,
        NOTIFICATION-GROUP
                    FROM SNMPv2-CONF
        dlinkIndustrialCommon
                    FROM DLINK-ID-REC-MIB;

    dlinkSwRebootMIB MODULE-IDENTITY
        LAST-UPDATED "201410280000Z"
        ORGANIZATION "D-Link Corp."
        CONTACT-INFO
            "        D-Link Corporation

             Postal: No. 289, Sinhu 3rd Rd., Neihu District,
                     Taipei City 114, Taiwan, R.O.C
             Tel:     +886-2-66000123
             E-mail: tsd@dlink.com.tw
            "
        DESCRIPTION
            "This MIB module defines objects for reboot function."
        REVISION "201410280000Z"
        DESCRIPTION
            "This is the first version of the MIB file.
            "
        ::= { dlinkIndustrialCommon 183 }

-- -----------------------------------------------------------------------------
    dRebootMIBNotifications    OBJECT IDENTIFIER ::= { dlinkSwRebootMIB 0 }
    dRebootMIBObjects          OBJECT IDENTIFIER ::= { dlinkSwRebootMIB 1 }
    dRebootMIBConformance      OBJECT IDENTIFIER ::= { dlinkSwRebootMIB 2 }
-- -----------------------------------------------------------------------------

    dRebootScheduleTable OBJECT-TYPE
        SYNTAX  SEQUENCE OF DRebootScheduleEntry
        MAX-ACCESS  not-accessible
        STATUS  current
        DESCRIPTION
            "The management table for reboot schedule."
        ::= { dRebootMIBObjects 1 }

    dRebootScheduleEntry OBJECT-TYPE
        SYNTAX  DRebootScheduleEntry
        MAX-ACCESS  not-accessible
        STATUS  current
        DESCRIPTION
            "A reboot schedule configuration entry."
        INDEX   { dRebootScheduleIndex }
        ::= { dRebootScheduleTable 1 }

    DRebootScheduleEntry  ::= SEQUENCE {
        dRebootScheduleIndex            Integer32,
        dRebootScheduleInterval         Unsigned32,
        dRebootScheduleSpceficTime      OCTET STRING,
        dRebootScheduleDate             OCTET STRING,
        dRebootScheduleSave             INTEGER,
        dRebootScheduleRowStatus        RowStatus
        }

    dRebootScheduleIndex OBJECT-TYPE
        SYNTAX      Integer32 (1..2147483647)
        MAX-ACCESS  not-accessible
        STATUS      current
        DESCRIPTION
            "The table index for the reboot schedule.
             If the device only supports to configure one reboot schedule, the 
             index must be set to 1."
        ::= { dRebootScheduleEntry 1 }

    dRebootScheduleInterval OBJECT-TYPE
        SYNTAX      Unsigned32 (0..43200)
        MAX-ACCESS  read-write
        STATUS      current
        DESCRIPTION
            "Specifies the reboot happens after a specified time interval is passed.
             The range of time interval is 0-43200 minutes.
             If the value is 0, this object is not used."
        ::= { dRebootScheduleEntry 2 }

    dRebootScheduleSpceficTime OBJECT-TYPE
        SYNTAX      OCTET STRING (SIZE (2))
        MAX-ACCESS  read-write
        STATUS      current
        DESCRIPTION
            "Indicates the reboot specific time by schedule.
                 octets    contents    range
                 1         hour        0..23
                 2         min         0..59
                 For example, 13:30
                 should be given as 0d 1e."
        ::= { dRebootScheduleEntry 3 }

    dRebootScheduleDate OBJECT-TYPE
        SYNTAX      OCTET STRING (SIZE (4))
        MAX-ACCESS  read-write
        STATUS      current
        DESCRIPTION
            "Indicates the data of reboot time by schedule.
                 octets     contents    range
                 1          monthDay    1..31
                 2          month       1..12
                                        where january = 1 december = 12
                 3-4        year        2000..2100
                 For example, 06 july 2012
                 should be given as 06 07 07 dc."
        ::= { dRebootScheduleEntry 4 }

    dRebootScheduleSave OBJECT-TYPE
        SYNTAX  INTEGER {
                    yes(1),
                    no(2)
                }
        MAX-ACCESS  read-write
        STATUS      current
        DESCRIPTION
            "Specifies the device will save all configurations before the reboot
             happens."
        ::= { dRebootScheduleEntry 5}

    dRebootScheduleRowStatus OBJECT-TYPE
        SYNTAX      RowStatus
        MAX-ACCESS  read-create
        STATUS      current
        DESCRIPTION
            "The row status variable, used according to installation
            and removal conventions for conceptual rows.
            "
        ::= { dRebootScheduleEntry 99 }

-- -----------------------------------------------------------------------------

    dRebootNode OBJECT-TYPE
        SYNTAX  INTEGER {
                    none(1),
                    start(2)
                }
        MAX-ACCESS  read-write
        STATUS      current
        DESCRIPTION
            "Used to restart the switch."
        ::= { dRebootMIBObjects 2 }

-- -----------------------------------------------------------------------------
--  Notifications
-- -----------------------------------------------------------------------------
    dRebootScheduleRebootIn5Min NOTIFICATION-TYPE
        STATUS  current
        DESCRIPTION
            "This trap contains the RebootIn5Min."
        ::= { dRebootMIBNotifications 1 }

    dRebootScheduleRebootIn1Min NOTIFICATION-TYPE
        STATUS  current
        DESCRIPTION
            "This trap contains the RebootIn1Min."
        ::= { dRebootMIBNotifications 2 }

-- -----------------------------------------------------------------------------
-- MIB Conformance statements
-- -----------------------------------------------------------------------------
    dRebootRebootMIBCompliances     OBJECT IDENTIFIER ::= { dRebootMIBConformance 1 }
    dRebootRebootMIBGroup           OBJECT IDENTIFIER ::= { dRebootMIBConformance 2 }
    
-- compliance statements
    dRebootRebootMIBCompliance MODULE-COMPLIANCE
        STATUS      current
        DESCRIPTION
            "The compliance statement for reboot which
             implement the DLINKSW-REBOOT-MIB."
        MODULE      -- this module
        MANDATORY-GROUPS       {
            dRebootScheduleGroup,
            dRebootMIBGroup,
            dRebootNotificationGroup
        }
        GROUP dRebootScheduleGroup
            DESCRIPTION
                "Implementation of this group description the rebootschedule."

        ::= { dRebootRebootMIBCompliances 1 }

    dRebootScheduleGroup OBJECT-GROUP
        OBJECTS   {
            dRebootScheduleInterval,
            dRebootScheduleSpceficTime,
            dRebootScheduleDate,
            dRebootScheduleSave,
            dRebootScheduleRowStatus
        }
        STATUS      current
        DESCRIPTION
            "A collection of objects configures the reboot schedule feature."
        ::= { dRebootRebootMIBGroup 1 }

    dRebootMIBGroup OBJECT-GROUP
        OBJECTS   {
            dRebootNode
        }
        STATUS      current
        DESCRIPTION
            "A collection of objects configures the reboot schedule feature."
        ::= { dRebootRebootMIBGroup 2 }

    dRebootNotificationGroup NOTIFICATION-GROUP
        NOTIFICATIONS {
            dRebootScheduleRebootIn5Min,
            dRebootScheduleRebootIn1Min
        }
        STATUS current
        DESCRIPTION
            "The Reboot MIB Notification Group."
        ::= { dRebootRebootMIBGroup 3 }

END
