--  *****************************************************************
--  DLINKES-SNMP-MIB.mib : SNMP management MIB
--
--  Copyright (c) 2013 D-Link Corporation, all rights reserved.
--
--  *****************************************************************
DLINKES-SNMP-MIB DEFINITIONS ::= BEGIN

	IMPORTS
   		MODULE-IDENTITY, OBJECT-TYPE, NOTIFICATION-TYPE, Unsigned32        
       		FROM SNMPv2-SMI
   		DisplayString, TruthValue, TEXTUAL-CONVENTION
       		FROM SNMPv2-TC
   		MODULE-COMPLIANCE, OBJECT-GROUP, NOTIFICATION-GROUP
       		FROM SNMPv2-CONF               		
        SnmpAdminString, SnmpSecurityModel                      
            FROM SNMP-FRAMEWORK-MIB
        ifIndex, InterfaceIndexOrZero
            FROM IF-MIB                  
   		dlinkCommon		
            FROM DLINK-ID-REC-MIB;
       
   
   dlinkEsSnmpMIB	MODULE-IDENTITY
   		LAST-UPDATED "201304150000Z"
   		ORGANIZATION "D-Link Corp."
        CONTACT-INFO
            "        D-Link Corporation

             Postal: No. 289, Sinhu 3rd Rd., Neihu District,
                     Taipei City 114, Taiwan, R.O.C
             Tel:     +886-2-66000123
             E-mail: tsd@dlink.com.tw
            "
        DESCRIPTION
            "This MIB module defines objects for configuring SNMP 
            ( Simple Network Management Protocol )"
            
        REVISION "201304150000Z"
        DESCRIPTION
            "This is the first version of the MIB file for 'SNMP'
            functionality."  
       
        ::= { dlinkCommon 2 } 
            
	esSnmpMIBNotifications 	OBJECT IDENTIFIER ::= { dlinkEsSnmpMIB 0 }
	esSnmpMIBObjects 		OBJECT IDENTIFIER ::= { dlinkEsSnmpMIB 1 }
	esSnmpMIBConformance		OBJECT IDENTIFIER ::= { dlinkEsSnmpMIB 2 }
    
-- Textual Conventions used in the SNMP Management Architecture ***

SnmpEngineID ::= TEXTUAL-CONVENTION
    STATUS       current
    DESCRIPTION "An SNMP engine's administratively-unique identifier.
                 Objects of this type are for identification, not for
                 addressing, even though it is possible that an
                 address may have been used in the generation of
                 a specific value.

                "
    SYNTAX       OCTET STRING (SIZE(5..32))

SnmpSecurityModel ::= TEXTUAL-CONVENTION
    STATUS       current
    DESCRIPTION "An identifier that uniquely identifies a
                 securityModel of the Security Subsystem within the
                 SNMP Management Architecture.

                 The values for securityModel are allocated as
                 follows:
                "
    SYNTAX       INTEGER(0 .. 2147483647)
	
-- -------------------------------------------------------------------------- 
	esSnmpGeneral			OBJECT IDENTIFIER ::= { esSnmpMIBObjects 1 }
		
	esSnmpServiceEnabled OBJECT-TYPE
   		SYNTAX          TruthValue
  		MAX-ACCESS      read-write
   		STATUS          current
   		DESCRIPTION
           "A Boolean value represents the SNMP server is Enabled or Disabled."
   		::= { esSnmpGeneral 1 }
   	
   	esSnmpServiceUdpPort OBJECT-TYPE
   		SYNTAX          Unsigned32
  		MAX-ACCESS      read-write
   		STATUS          current
   		DESCRIPTION
           "This object indicates the SNMP UDP port number.
           By default, the SNMP agent receives requests on UDP port 161."
   		::= { esSnmpGeneral 2 }
   
   	esSnmpRspBcastRequestEnabled OBJECT-TYPE
   		SYNTAX          TruthValue
  		MAX-ACCESS      read-write
   		STATUS          current
   		DESCRIPTION
           "A Boolean value represents whether response broadcast SNMP
           GetRequest packet."
   		::= { esSnmpGeneral 3 }
   	          
    esSnmpLocalEngineID OBJECT-TYPE
        SYNTAX          SnmpEngineID
        MAX-ACCESS      read-write
        STATUS          current
        DESCRIPTION
            "This object indicates the agent's local engineID value.
            Changing this variable will affect the value of snmpEngineID. 
            The special value of '00 00 00 00 00'H indicates the local engineID 
            is not specified, and snmpEngineID will be automatically created
            based on the device basic MAC address.
            The SNMP engine ID is a unique string to identify the device. 
            The string is generated by default. Check RFC3411 for further
            details on the SNMP engine ID."       
        ::= { esSnmpGeneral 4 }   
        
-- -------------------------------------------------------------------------- 
	esSnmpMIBTrap				OBJECT IDENTIFIER ::= { esSnmpMIBObjects 2 }
	
	esSnmpTrapGlobalEnabled OBJECT-TYPE
       	SYNTAX          TruthValue
  		MAX-ACCESS      read-write
   		STATUS          current
   		DESCRIPTION
            "A Boolean value to represent the global state of sending of trap
            packets.
            "
   		::= { esSnmpMIBTrap 1 }

    esSnmpTrapGlobalNotifyEnable OBJECT-TYPE
        SYNTAX          BITS {         
            linkUp(0),
            linkDown(1),
            coldStart(2),
            warmStart(3),
            authentication(4)
        }
        MAX-ACCESS  read-write
        STATUS      current
        DESCRIPTION
            "This object indicates global state about whether a specified
            notification is enabled or not.
            If a bit corresponding to a notification is set to 1, then 
            the specified notification can be generated.

            linkUp(0)    - sending a standard linkUp notification (defined in IF-MIB). 
            linkDown(1)  - sending a standard linkDown notification (defined in IF-MIB).  
            coldStart(2) - sending a standard coldStart notification (defined in SNMPv2-MIB).
            warmStart(3) - sending a standard warmStart notification (defined in SNMPv2-MIB).
            Note: please use snmpEnableAuthenTraps (defined in SNMPv2-MIB) to control 
            the generation of authenticationFailure traps.
            "
        ::= { esSnmpMIBTrap 2 }
      
    esSnmpTrapSourceIfIndex  OBJECT-TYPE
        SYNTAX          InterfaceIndexOrZero
        MAX-ACCESS      read-write
        STATUS          current
        DESCRIPTION
            "The ifIndex of the interface whose IP address is used as the
            source IP address for outbound SNMP traps.
            A special value of zero indicates the source interface is not
            specified, the IP address of the closest interface will be used.           
            "
        ::= { esSnmpMIBTrap 3 }		   
-- -------------------------------------------------------------------------- 	
	esSnmpTrapIfCtrl			OBJECT IDENTIFIER ::= { esSnmpMIBTrap 4 }
                        
    esSnmpTrapIfCfgTable	OBJECT-TYPE
		SYNTAX          SEQUENCE OF EsSnmpTrapIfCfgEntry
		MAX-ACCESS      not-accessible
        STATUS          current
        DESCRIPTION
            "This table contains a list of interface-specific notification
            configuration.
            "
        ::= {esSnmpTrapIfCtrl 1}
      
    esSnmpTrapIfCfgEntry	OBJECT-TYPE
		SYNTAX	        EsSnmpTrapIfCfgEntry
		MAX-ACCESS      not-accessible
        STATUS          current
        DESCRIPTION
            "An entry manages notification on an interface."
        INDEX  {  ifIndex }
      ::= {esSnmpTrapIfCfgTable 1}
      
    EsSnmpTrapIfCfgEntry ::=
        SEQUENCE {
            esSnmpTrapIfSendTrapEnabled     TruthValue
        }  
   	
   	esSnmpTrapIfSendTrapEnabled OBJECT-TYPE
        SYNTAX          TruthValue
        MAX-ACCESS      read-create
        STATUS          current
        DESCRIPTION     
            "This object indicates whether sending trap on the interface.
            If the state is disabled, then SNMP notification traps generated
            by the system are not allowed to transmit out of the port. 
            " 
        DEFVAL { true }
        ::= { esSnmpTrapIfCfgEntry 1 }
        
   
-- -------------------------------------------------------------------------- 	 
	esSnmpRmonRisingAlarmTrapEnabled OBJECT-TYPE
       	SYNTAX          TruthValue
  		MAX-ACCESS      read-write
   		STATUS          current
   		DESCRIPTION
            "A Boolean value to represent the global state of sending of RMON
            rising-alarm trap packets.
            "
   		::= { esSnmpMIBTrap 5 }

	esSnmpRmonFallingAlarmTrapEnabled OBJECT-TYPE
       	SYNTAX          TruthValue
  		MAX-ACCESS      read-write
   		STATUS          current
   		DESCRIPTION
            "A Boolean value to represent the global state of sending of RMON
            falling-alarm trap packets.
            "
   		::= { esSnmpMIBTrap 6 }

        		
-- -------------------------------------------------------------------------- 	 
    esSnmpAccessCfg 			OBJECT IDENTIFIER ::= { esSnmpMIBObjects 3 }
         
    esSnmpCommunityTable  OBJECT-TYPE
        SYNTAX          SEQUENCE OF EsSnmpCommunityEntry
        MAX-ACCESS      not-accessible
        STATUS          current
        DESCRIPTION
            "This table consists of a list of communities.
            "       
        ::= { esSnmpAccessCfg 1 }

    esSnmpCommunityEntry  OBJECT-TYPE
        SYNTAX          EsSnmpCommunityEntry
        MAX-ACCESS      not-accessible
        STATUS          current
        DESCRIPTION
            "An entry defines additional information which is not covered at
            snmpCommunityTable (defined in SNMP-COMMUNITY-MIB).
            An entry appears in this table when a community is created in 
            snmpCommunityTable.
            "
        INDEX     { esSnmpCommunityName }
        ::= { esSnmpCommunityTable 1 }

    EsSnmpCommunityEntry ::= SEQUENCE {
        esSnmpCommunityName               SnmpAdminString,
        esSnmpCommunityAccessListName     DisplayString       
    }

    esSnmpCommunityName  OBJECT-TYPE
        SYNTAX          SnmpAdminString
        MAX-ACCESS      not-accessible
        STATUS          current
        DESCRIPTION
           "This object indicates the name of the community."
        ::= { esSnmpCommunityEntry 1 }
   	
    esSnmpCommunityAccessListName  OBJECT-TYPE
        SYNTAX          DisplayString 
        MAX-ACCESS      read-write
        STATUS          current
        DESCRIPTION
           "This object indicates the name of a standard access list to control
           the user to use this community string to access to the SNMP agent. 
           Specify the valid user in the source address field of the access 
           list entry.
           A zero length string indicates the access list is not specified.          
           "
        ::= { esSnmpCommunityEntry 3 }

-- --------------------------------------------------------------------------
    esSnmpGroupTable  OBJECT-TYPE
        SYNTAX          SEQUENCE OF EsSnmpGroupEntry
        MAX-ACCESS      not-accessible
        STATUS          current
        DESCRIPTION
            "This table consists of a list of groups.
            "       
        ::= { esSnmpAccessCfg 2 }

    esSnmpGroupEntry  OBJECT-TYPE
        SYNTAX          EsSnmpGroupEntry
        MAX-ACCESS      not-accessible
        STATUS          current
        DESCRIPTION
            "An entry consists of additional informaiton which is not covered
            at vacmAccessTable (defined in SNMP-VIEW-BASED-ACM-MIB).
            An entry appears in this table when a group is created in 
            vacmAccessTable or vacmSecurityToGroupTable.
            "
        INDEX     { 
            esSnmpGroupName ,
        	esSnmpGroupVersion
        }
        ::= { esSnmpGroupTable 1 }

    EsSnmpGroupEntry ::= SEQUENCE {
        esSnmpGroupName               SnmpAdminString,  
        esSnmpGroupVersion            SnmpSecurityModel,
        esSnmpGroupAccessListName     DisplayString       
    }

    esSnmpGroupName  OBJECT-TYPE
        SYNTAX          SnmpAdminString
        MAX-ACCESS      not-accessible
        STATUS          current
        DESCRIPTION
           "This object indicates the name of the group."
        ::= { esSnmpGroupEntry 1 }
    
    esSnmpGroupVersion  OBJECT-TYPE 
      SYNTAX          SnmpSecurityModel 
      MAX-ACCESS      not-accessible 
      STATUS          current 
      DESCRIPTION 
         "This object indicates the version of the entry." 
      ::= { esSnmpGroupEntry 2 } 

       	
    esSnmpGroupAccessListName  OBJECT-TYPE
        SYNTAX          DisplayString
        MAX-ACCESS      read-write
        STATUS          current
        DESCRIPTION
           "This object indicates the name of a standard access control list
           (ACL) to associate with the group.
           A zero length string indicates the access list is not specified.  
           "
        ::= { esSnmpGroupEntry 3 }
        
-- --------------------------------------------------------------------------
    esSnmpHostTable  OBJECT-TYPE
        SYNTAX          SEQUENCE OF EsSnmpHostEntry
        MAX-ACCESS      not-accessible
        STATUS          current
        DESCRIPTION
            "This table consists of a list of recipients for the SNMP
            notification. 
            "       
        ::= { esSnmpAccessCfg 3 }

    esSnmpHostEntry  OBJECT-TYPE
        SYNTAX          EsSnmpHostEntry
        MAX-ACCESS      not-accessible
        STATUS          current
        DESCRIPTION
            "An entry consists of additional informaiton which is not covered
            at snmpTargetAddrTable and snmpTargetParamsTable (defined in 
            SNMP-TARGET-MIB).           
            An entry appears in this table when a target address is created in 
            snmpTargetAddrTable.
            "            
        INDEX     { esSnmpHostAddrName }
        ::= { esSnmpHostTable 1 }

    EsSnmpHostEntry ::= SEQUENCE {
        esSnmpHostAddrName            SnmpAdminString,
        esSnmpHostVrfName             DisplayString,
        esSnmpHostUdpPort             Unsigned32     
    }

    esSnmpHostAddrName  OBJECT-TYPE
        SYNTAX          SnmpAdminString (SIZE(1..32))
        MAX-ACCESS      not-accessible
        STATUS          current
        DESCRIPTION
           "This object indicates the address name of the recipients."
        ::= { esSnmpHostEntry 1 }
    
    esSnmpHostVrfName  OBJECT-TYPE
        SYNTAX          DisplayString 
        MAX-ACCESS      read-write
        STATUS          current
        DESCRIPTION
           "This object indicates the name of the routing forwarding instance.
           A zero length string indicates the object is not specified.
           "
        ::= { esSnmpHostEntry 2 }
           	
    esSnmpHostUdpPort  OBJECT-TYPE
        SYNTAX          Unsigned32
        MAX-ACCESS      read-write
        STATUS          current
        DESCRIPTION
           "This object indicates trap UDP port number."
        DEFVAL { 162 }
        ::= { esSnmpHostEntry 3 }        

-- --------------------------------------------------------------------------        
    esSnmpUserTable  OBJECT-TYPE
        SYNTAX          SEQUENCE OF EsSnmpUserEntry
        MAX-ACCESS      not-accessible
        STATUS          current
        DESCRIPTION
            "This table consists of a list of recipients for the SNMP
            notification. 
            "       
        ::= { esSnmpAccessCfg 4 }

    esSnmpUserEntry  OBJECT-TYPE
        SYNTAX          EsSnmpUserEntry
        MAX-ACCESS      not-accessible
        STATUS          current
        DESCRIPTION
            "An entry consists of additional informaiton which is not covered
            at usmUserTable (defined in SNMP-USER-BASED-SM-MIB).           
            An entry appears in this table when a user is created in 
            usmUserTable.
            "            
        INDEX     { esSnmpUserName }
        ::= { esSnmpUserTable 1 }

     EsSnmpUserEntry ::= SEQUENCE {
        esSnmpUserName               SnmpAdminString,       
        esSnmpUserAccessListName     DisplayString       
    }

    esSnmpUserName  OBJECT-TYPE
        SYNTAX          SnmpAdminString (SIZE(1..32))
        MAX-ACCESS      not-accessible
        STATUS          current
        DESCRIPTION
           "This object indicates the name of the user."
        ::= { esSnmpUserEntry 1 }
   	
    esSnmpUserAccessListName  OBJECT-TYPE
        SYNTAX          DisplayString
        MAX-ACCESS      read-write
        STATUS          current
        DESCRIPTION
           "This object indicates the name of a standard IP access control
           list (ACL) to associate with the user.
           A zero length string indicates the access list is not specified.  
           "
        ::= { esSnmpUserEntry 2 }
        
--  ***************************************************************************	
--  Conformance
--  ***************************************************************************			   		
	esSnmpCompliances OBJECT IDENTIFIER ::= { esSnmpMIBConformance 1 }
		
	esSnmpCompliance MODULE-COMPLIANCE
		STATUS current
		DESCRIPTION 
			"The compliance statement for entities which implement the 
			DLINKES-SNMP-MIB."
		MODULE -- this module
		MANDATORY-GROUPS { 
		    esSnmpSysCfgGroup,
		    esSnmpTrapCfgGroup		   		   
		}
				
		GROUP    esSnmpTargetExtGroup 
        DESCRIPTION
           "This group is conditionally mandatory and must be implemented by
		    the agent only if extensions of community is supported."
		OBJECT      esSnmpHostVrfName
		MIN-ACCESS  read-only
		DESCRIPTION
		    "This object is conditionally mandatory and must be implemented by
		    the agent only if the implementation supports VRF based reachability
            and filtering for SNMP targets."
        
        GROUP    esSnmpTrapIfCfgGroup 
        DESCRIPTION
           "This group is conditionally mandatory and must be implemented by
		    the agent only if interface-specific control of traps is supported."
		::= { esSnmpCompliances 1 }

-- units of conformance		
	esSnmpGroups OBJECT IDENTIFIER ::= { esSnmpMIBConformance 2 }
		
	esSnmpSysCfgGroup OBJECT-GROUP
		OBJECTS { 
		    esSnmpServiceEnabled,
		    esSnmpServiceUdpPort,
		    esSnmpRspBcastRequestEnabled,
		    esSnmpLocalEngineID		    
		}
		STATUS current
		DESCRIPTION 
			"A collection of objects provides the information for SNMP server."
		::= { esSnmpGroups 1 }
		
	esSnmpTrapCfgGroup OBJECT-GROUP
		OBJECTS { 
		    esSnmpTrapGlobalEnabled,
		    esSnmpTrapGlobalNotifyEnable,
		    esSnmpTrapSourceIfIndex,
		    esSnmpRmonRisingAlarmTrapEnabled,
		    esSnmpRmonFallingAlarmTrapEnabled
		}
		STATUS current
		DESCRIPTION 
			"A collection of objects provides system-wide control of traps."
			::= { esSnmpGroups 2 }
	
	esSnmpTrapIfCfgGroup OBJECT-GROUP
		OBJECTS { 		    
		    esSnmpTrapIfSendTrapEnabled
		    
		}
		STATUS current
		DESCRIPTION 
			"A collection of objects provides interface-specific control of traps."
			::= { esSnmpGroups 3 }
	
	esSnmpCommunityExtGroup OBJECT-GROUP
        OBJECTS         { 
            esSnmpCommunityAccessListName
        }
        STATUS          current
        DESCRIPTION
            "The collection of objects provides configuration for community feature
            which extends SNMP community. 
            "
    ::= { esSnmpGroups 4 }
    			
    esSnmpTargetExtGroup OBJECT-GROUP
        OBJECTS         {                    
            esSnmpHostVrfName,
            esSnmpHostUdpPort     
        }
        STATUS          current
        DESCRIPTION
        
         "The collection of objects provides configuration for recipient of the
        SNMP notification."
        ::= { esSnmpGroups 5 }
    	
	esSnmpVacmExtGroup  OBJECT-GROUP
        OBJECTS        { 
            esSnmpGroupAccessListName,
            esSnmpUserAccessListName 
        }
        STATUS         current
        DESCRIPTION
           "A collection of objects providing for remote configuration of an SNMP
           engine which extends the SNMP VACM (View-based Access Control Model) and 
           USM (User-based Security Model)."
        ::= { esSnmpGroups 6 }
    
	


END
