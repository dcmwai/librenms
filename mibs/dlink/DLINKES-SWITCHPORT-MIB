--  *****************************************************************
--  DLINKES-SWITCHPORT-MIB.mib : Switch Port MIB
--
--  Copyright (c) 2013 D-Link Corporation, all rights reserved.
--
--  *****************************************************************
DLINKES-SWITCHPORT-MIB DEFINITIONS ::= BEGIN

    IMPORTS
        MODULE-IDENTITY,
        OBJECT-TYPE,
        Unsigned32
                FROM SNMPv2-SMI
        TruthValue
                FROM SNMPv2-TC
        MODULE-COMPLIANCE, OBJECT-GROUP 
                FROM SNMPv2-CONF
        ifIndex
                FROM IF-MIB
        dlinkCommon
                FROM DLINK-ID-REC-MIB;
                
    dlinkEsSwitchPortMIB MODULE-IDENTITY    
        LAST-UPDATED "202003110000Z"
        ORGANIZATION "D-Link Corp."
        CONTACT-INFO
            "        D-Link Corporation

             Postal: No. 289, Sinhu 3rd Rd., Neihu District,
                     Taipei City 114, Taiwan, R.O.C
             Tel:     +886-2-66000123
             E-mail: tsd@dlink.com.tw
            "
        DESCRIPTION
            "This MIB module defines objects for per-port configuration which 
            are not covered by standard MIB(s)."
			
        REVISION "202003110000Z"
        DESCRIPTION
		    "obsolete dSwPortIfB1000baseTCtrl & dSwPortIfB10GbaseTCtrl
		    add dSwPortIfMasterSlaveType"
        REVISION "201910160000Z"
        DESCRIPTION
		    "Add new object -dSwPortIfUnidirectional.
		    Modify compliance part"

        REVISION "201303040000Z"
        DESCRIPTION
            " This is the first version of the MIB file
            "
        ::= { dlinkCommon 11 }

-- -----------------------------------------------------------------------------
    esSwPortNotifications    OBJECT IDENTIFIER ::= { dlinkEsSwitchPortMIB 0 }
    esSwPortObjects          OBJECT IDENTIFIER ::= { dlinkEsSwitchPortMIB 1 }
    esSwPortConformance      OBJECT IDENTIFIER ::= { dlinkEsSwitchPortMIB 2 }


-- -----------------------------------------------------------------------------
-- Objects
-- -----------------------------------------------------------------------------         
     esSwPortIfTable OBJECT-TYPE
        SYNTAX          SEQUENCE OF EsSwPortIfEntry
        MAX-ACCESS      not-accessible
        STATUS          current
        DESCRIPTION
            "A list of physical port interface entries."
        ::= { esSwPortObjects 1 }
        
    esSwPortIfEntry OBJECT-TYPE
	    SYNTAX          EsSwPortIfEntry
	    MAX-ACCESS      not-accessible
	    STATUS          current
	    DESCRIPTION 
	        "An entry in esSwPortIfTable contains port-specific configuration
		    which cannot be covered by standard MIBs (EtherLike or MAU-MIB)."
	    INDEX       { ifIndex }
	    ::= { esSwPortIfTable 1 } 
	    
    EsSwPortIfEntry ::= SEQUENCE {            
        esSwPortIfB1000baseTCtrl     INTEGER,        
        esSwPortIfB10GbaseTCtrl      INTEGER,         
        esSwPortIfMdix               INTEGER,
        esSwPortIfJumboFrameSize     Unsigned32,
        esSwPortIfSpeedAutoDowngrade TruthValue,
        esSwPortLinkChangeLogState   TruthValue,   
        esSwPortIfUnidirectional     INTEGER,      
        esSwPortIfMasterSlaveType    INTEGER  
    }
   
    esSwPortIfB1000baseTCtrl OBJECT-TYPE
        SYNTAX          INTEGER { 
            other(1),           
            b1000baseTMaster(2),
            b1000baseTSlave(3)                          
        }
        MAX-ACCESS      read-write
        STATUS          obsolete
        DESCRIPTION      
            "This object can be modified when port speed is configured to 1000BASE-T. 
            other(1) - the port is not 1000BASE-T or master/slave timing mode
                       is not specified.
            b1000baseTMaster(2) - configure the port operate as master timing.
            b1000baseTSlave(3) - configure the port operate as slave timing.                    
            "     
        DEFVAL      { b1000baseTMaster }      
        ::= { esSwPortIfEntry 1 }

    esSwPortIfB10GbaseTCtrl OBJECT-TYPE
        SYNTAX          INTEGER { 
            other(1),           
            b10GbaseTMaster(2),
            b10GbaseTSlave(3)                          
        }
        MAX-ACCESS      read-write
        STATUS          obsolete
        DESCRIPTION      
            "This object can be modified when port speed is configured to 10GBASE-T. 
            other(1) - the port is not 10GBASE-T or master/slave timing mode
                       is not specified.
            b10GbaseTMaster(2) - configure the port operate as master timing.
            b10GbaseTSlave(3) - configure the port operate as slave timing.                    
            "     
        DEFVAL      { b10GbaseTMaster }      
        ::= { esSwPortIfEntry 2 }
                
    esSwPortIfMdix OBJECT-TYPE
        SYNTAX      INTEGER { 
            auto(1), 
            normal(2), 
            cross(3) 
        }
        MAX-ACCESS  read-write
        STATUS      current
        DESCRIPTION   
            "Uses the object to configure the state of Media-Dependent Interface
            Crossover (MDIX) of the port."
        DEFVAL      { auto }
        ::= { esSwPortIfEntry 3 }
	
    esSwPortIfJumboFrameSize OBJECT-TYPE
	    SYNTAX		    Unsigned32
	    MAX-ACCESS	    read-write
	    STATUS		    current
	    DESCRIPTION
			"The size of the largest packet which can be received on the
			interface, specified in octets."
		DEFVAL      { 1536 }	
	    ::= { esSwPortIfEntry 4 }

    esSwPortIfSpeedAutoDowngrade OBJECT-TYPE
	    SYNTAX		TruthValue
	    MAX-ACCESS	    	read-write
	    STATUS		current
	    DESCRIPTION
			"This object indicates whether automatically downgrade the advertised
            speed in case a link cannot be established at the available speed. 
			"
		DEFVAL      { false }	
	    ::= { esSwPortIfEntry 5 }	    
	    	    
    esSwPortLinkChangeLogState OBJECT-TYPE
        SYNTAX          TruthValue
        MAX-ACCESS      read-write
        STATUS          current
        DESCRIPTION
            "port link change log state."
        DEFVAL      { true }
        ::= { esSwPortIfEntry 6 }         
         
     esSwPortIfUnidirectional OBJECT-TYPE
        SYNTAX          INTEGER
        {  
         none(1),
         sendOnly(2),
         receiveOnly(3)
        }
        MAX-ACCESS      read-write
        STATUS          current
        DESCRIPTION
            "UDE provides the capability of unidirectional link in order to 
            satisfy the particular application requirements.
            sendOnly mode will make port force linkup even if there has 
            is no gbic plug in and cable connecting.
            "
        DEFVAL      { none }
        ::= { esSwPortIfEntry 7 }   
       
    esSwPortIfMasterSlaveType OBJECT-TYPE
        SYNTAX          INTEGER { 
            other(1),           
            b1000BaseTMaster(2),        
            b1000BaseTSlave(3),        
            b10GBaseTMaster(4),               
            b10GBaseTSlave(5),               
            b2500BaseTMaster(6),
            b2500BaseTSlave(7),  
            b5GBaseTMaster(8),
            b5GBaseTSlave(9)                    
        }
        MAX-ACCESS      read-write
        STATUS          current
        DESCRIPTION      
            "This object configure the master/slave role.              
            "     
        DEFVAL      { other }      
        ::= { esSwPortIfEntry 8 }
		

-- -----------------------------------------------------------------------------
-- Conformance
-- -----------------------------------------------------------------------------
    esSwPortCompliances OBJECT IDENTIFIER ::= { esSwPortConformance 1 }
		
	esSwPortCompliance MODULE-COMPLIANCE
		STATUS          current
		DESCRIPTION 
			"The compliance statement for entities which implement the 
			DLINKES-SWITCHPORT-MIB."
		MODULE -- this module
		MANDATORY-GROUPS { 
		    esSwPortBasicGroup
		}		
	                        
        OBJECT          esSwPortIfSpeedAutoDowngrade        
        MIN-ACCESS      read-only
        DESCRIPTION
            "It is compliant to implement this object as
            read-only. The write-access is only required
            when auto-downgrade feature is supported."
	    ::= { esSwPortCompliances 1 }
		
	esSwPortGroups OBJECT IDENTIFIER ::= { esSwPortConformance 2 }
		
    esSwPortBasicGroup OBJECT-GROUP
		OBJECTS { 
		    esSwPortIfB1000baseTCtrl,
		    esSwPortIfB10GbaseTCtrl,
		    esSwPortIfMdix,
		    esSwPortIfJumboFrameSize,
		    esSwPortIfSpeedAutoDowngrade
		}
		STATUS current
		DESCRIPTION 
			"This group contains the collection of fundamental port configuration
			objects which are not covered by standard MIBs."						
		::= { esSwPortGroups 1 }
	

	
END
