--  *****************************************************************
--  DLINKES-DHCP-RELAY-MIB.mib : DHCP Relay MIB
--
--  Copyright (c) 2012 D-Link Corporation, all rights reserved.
--
--  *****************************************************************
DLINKES-DHCP-RELAY-MIB DEFINITIONS ::= BEGIN

    IMPORTS
        MODULE-IDENTITY,
        OBJECT-TYPE,
        IpAddress
                    FROM SNMPv2-SMI
        MODULE-COMPLIANCE,
        OBJECT-GROUP
                    FROM SNMPv2-CONF
        DisplayString,
        TruthValue,
        RowStatus
                    FROM SNMPv2-TC
        InterfaceIndex
                    FROM IF-MIB
        Dlink2kVlanList
                    FROM DLINKES-TC-MIB
        dlinkCommon
                    FROM DLINK-ID-REC-MIB;


    dlinkEsDhcpRelayMIB MODULE-IDENTITY
        LAST-UPDATED "201709260000Z"
        ORGANIZATION "D-Link Corp."
        CONTACT-INFO
            "        D-Link Corporation

             Postal: No. 289, Sinhu 3rd Rd., Neihu District,
                     Taipei City 114, Taiwan, R.O.C
             Tel:     +886-2-66000123
             E-mail: tsd@dlink.com.tw
            "
        DESCRIPTION
            "This MIB module defines objects for BOOTP/DHCP relay."

        REVISION "201709260000Z"
        DESCRIPTION
            "Remove unsuuported value of remote-ID and circuit-ID."

        REVISION "201708170000Z"
        DESCRIPTION
            "Remove not suuport key."

        REVISION "201702020000Z"
        DESCRIPTION
            "Modify mib object for EESDD."

        REVISION "201507070000Z"
        DESCRIPTION
             "1. Add the node dDhcpRRelayVlanCtrlTable"

        REVISION "201503310000Z"
        DESCRIPTION
            "1.Add the node dDhcpRIfAgentInfoStateCtrlTable."

        REVISION "201412150000Z"
        DESCRIPTION
            "1.Add the node dDhcpRelayAgentInfoIgnoreBootpEnabled.
             2.Deprecated the table dDhcpRIfIgnoreBootpTable."

        REVISION "201410140000Z"
        DESCRIPTION
            "1.Add the node dDhcpRelayAgentInfoInsertVPNEnabled and table dDhcpRIfAgentInfoInsertVPNTable to
               support the VPN-related suboptions for DHCP option 82.
             2. Add the node dDhcpRPoClRelayTargetVrfState and dDhcpRPoolRelayDestVrfState
               to support the virtual routing and forwarding (VRF).
             3. Modify the length for dDhcpROption82ExUdfProfileValue.
             4. Add the node dDhcpROption82RemoteExpertUdfUnitId and dDhcpROption82CircuitExpertUdfUnitId."

        REVISION "201403030000Z"
        DESCRIPTION
            "1.Add new Circuit ID type in dDhcpROption82CircuitIdType and dDhcpRPortIfOp82CirIdExpertUdfCfg: expertUdf(9).
             2.Add new Remote ID type in dDhcpROption82RemoteIdType and dDhcpRPortIfOp82RemIdExpertUdfCfg: expertUdf(6).
             3.Add dDhcpROption82ExUdfProfileTable, dDhcpROption82ExUdfMacFormatCase, dDhcpROption82ExUdfMacFormatDelimiter
              abd dDhcpROption82ExUdfMacFormatDelimiterNumber to support flexible user-defined DHCP option 82."

        REVISION "201401020000Z"
        DESCRIPTION
            "1.Update dDhcpROption82RemoteIdUserDef and dDhcpROption82CircuitIdUserDef value length(Note:follow UIS).
            2.Remove dDhcpRIfIgnoreBootpRowStatus and add dDhcpRIfIgnoreBootpEnabled(Note:follow IP interface).
            3.Remove dDhcpRIfAgentInfoChkRowStatus and modify dDhcpRIfAgentInfoChkState SYNTAX(Note:follow IP interface).
            4.Remove dDhcpRIfAgentInfoInsertRowStatus and modify dDhcpRIfAgentInfoInsertState SYNTAX(Note:follow IP interface).
            5.Remove dDhcpRIfAgentInfoPolicyRowStatus(Note:follow IP interface).
            6.Remove dDhcpRIfAgentInfoTrustRowStatus and add dDhcpRIfAgentInfoTrustEnabled(Note:follow IP interface)."

        REVISION "201309260000Z"
        DESCRIPTION
            "1.Modify dDhcpROption82RemoteIdUserDef and dDhcpROption82CircuitIdUserDef value length for IWL test.
             2.Update dDhcpRVlanLocalRelayCrlSecond2K description "

        REVISION "201307190000Z"
        DESCRIPTION
            "This is the first version of the MIB file for 'BOOTP/DHCP Relay'
             functionality."

        ::= { dlinkCommon 23 }

-- -----------------------------------------------------------------------------
    esDhcpRelayMIBNotifications    OBJECT IDENTIFIER ::= { dlinkEsDhcpRelayMIB 0 }
    esDhcpRelayMIBObjects          OBJECT IDENTIFIER ::= { dlinkEsDhcpRelayMIB 1 }
    esDhcpRelayMIBConformance      OBJECT IDENTIFIER ::= { dlinkEsDhcpRelayMIB 2 }

-- -----------------------------------------------------------------------------
    esDhcpRelayGeneral          OBJECT IDENTIFIER ::= { esDhcpRelayMIBObjects 1 }

    esDhcpRelayAgentInfoCheckEnabled OBJECT-TYPE
        SYNTAX          TruthValue
        MAX-ACCESS      read-write
        STATUS          current
        DESCRIPTION
            "This object indicates whether the DHCP relay agent validates the
             relay agent information option in the received DHCP reply packet."
        DEFVAL          { false }
        ::= { esDhcpRelayGeneral 1 }

    esDhcpRelayAgentInfoInsertEnabled OBJECT-TYPE
        SYNTAX          TruthValue
        MAX-ACCESS      read-write
        STATUS          current
        DESCRIPTION
            "This object indicates whether the DHCP relay agent inserts relay
            agent information option (option 82)."
        DEFVAL          { false }
        ::= { esDhcpRelayGeneral 2 }

    esDhcpRelayAgentInfoPolicy OBJECT-TYPE
        SYNTAX          INTEGER {  drop(1), keep(2), replace(3)}
        MAX-ACCESS      read-write
        STATUS          current
        DESCRIPTION
            "This object indicates the re-forwarding policy of DHCP relay agent
             information option 82.
             drop (1)    - discards the packet that already has the relay
                           option.
             keep (2)    - the DHCP requests packet that already has the relay
                           option is left unchanged and directly relayed to the
                           DHCP server.
             replace (3) - the DHCP requests packet that already has the relay
                           option will be replaced by a new option."
        DEFVAL          { replace }
        ::= { esDhcpRelayGeneral 3 }

    esDhcpRelayInfoTrustAll OBJECT-TYPE
        SYNTAX          TruthValue
        MAX-ACCESS      read-write
        STATUS          current
        DESCRIPTION
            "This object indicates whether the DHCP relay agent trusts the DHCP
            relay information for all interfaces."
        DEFVAL          { false }
        ::= { esDhcpRelayGeneral 4 }

    esDhcpROption82RemoteIdType OBJECT-TYPE
        SYNTAX  INTEGER {
            default(1),
            userDefined(2),
            vendor2(4),
            expertUdf(6)
        }
        MAX-ACCESS      read-write
        STATUS          current
        DESCRIPTION
            "This object indicates the type of remote ID sub-option.
            default(1)     - MAC address of VLAN 1.
            userDefined(2) - The value of esDhcpROption82RemoteID is used.
            vendor2(4)     - System Name.
            expertUdf(6)   - The flexible user defined format."
        ::= { esDhcpRelayGeneral 5 }

    esDhcpROption82RemoteIdUserDef OBJECT-TYPE
        SYNTAX          DisplayString (SIZE(0..32))
        MAX-ACCESS      read-write
        STATUS          current
        DESCRIPTION
            "This object indicates the global user defined string as the remote
            ID of the device.
            This object can be modified when esDhcpROption82RemoteIdType is set
            to 'userDefined'.
            When read, a zero length string is returned when esDhcpROption82RemoteIdType
            is not 'userDefined'."
        ::= { esDhcpRelayGeneral 6 }

    esDhcpROption82CircuitIdType OBJECT-TYPE
        SYNTAX  INTEGER {
            default(1),
            userDefined(2),
            vendor1(3),
            expertUdf(9)
        }
        MAX-ACCESS  read-write
        STATUS  current
        DESCRIPTION
            "This object indicates the type of circuit ID sub-option.
            default(1)     - VLAN ID, Module ID and Port Number.
            userDefined(2) - The value of esDhcpROption82CircuitID is used.
            vendor1(3)     - VLAN ID, Slot ID, Port Number and MAC address of VLAN 1.
            expertUdf(9)   - The flexible user defined format."
        ::= { esDhcpRelayGeneral 7 }

    esDhcpROption82CircuitIdUserDef OBJECT-TYPE
        SYNTAX      DisplayString (SIZE(0..32))
        MAX-ACCESS  read-write
        STATUS      current
        DESCRIPTION
            "This object indicates the global user defined string as the circuit ID.
            This object can be modified when esDhcpROption82CircuitIdType is set
            to 'userDefined'.
            When read, a zero length string is returned when esDhcpROption82CircuitIdType
            is not 'userDefined'."
        ::= { esDhcpRelayGeneral 8 }

    esDhcpRelayUnicast OBJECT-TYPE
        SYNTAX          TruthValue
        MAX-ACCESS      read-write
        STATUS          current
        DESCRIPTION
            "This object indicates the status of relaying DHCP client unicast packet."
        DEFVAL          { true }
        ::= { esDhcpRelayGeneral 9 }


-- -----------------------------------------------------------------------------
-- -----------------------------------------------------------------------------
    esDhcpRPoolObjects          OBJECT IDENTIFIER ::= { esDhcpRelayMIBObjects 2 }

    esDhcpRPoolClassRelayTargetTable OBJECT-TYPE
        SYNTAX      SEQUENCE OF EsDhcpRPoolClassRelayTargetEntry
        MAX-ACCESS  not-accessible
        STATUS      current
        DESCRIPTION
            "A table that contains relay target class configuration for DHCP pools."
        ::= { esDhcpRPoolObjects 1 }

    esDhcpRPoolClassRelayTargetEntry OBJECT-TYPE
        SYNTAX      EsDhcpRPoolClassRelayTargetEntry
        MAX-ACCESS  not-accessible
        STATUS      current
        DESCRIPTION
            "By using DHCP class, DHCP relay uses option configuration to further
            determine which DHCP relay target for relaying the packet that
            matches the value pattern of option defined in the class."
        INDEX {
            esDhcpRPoClRelayTargetPoolName,
            esDhcpRPoClRelayTargetClassName,
            esDhcpRPoClRelayTargetAddr}
       ::= { esDhcpRPoolClassRelayTargetTable 1 }

    EsDhcpRPoolClassRelayTargetEntry ::=     SEQUENCE {
        esDhcpRPoClRelayTargetPoolName       DisplayString,
        esDhcpRPoClRelayTargetClassName      DisplayString,
        esDhcpRPoClRelayTargetAddr           IpAddress,
        esDhcpRPoClRelayTargetRowStatus      RowStatus
    }

    esDhcpRPoClRelayTargetPoolName OBJECT-TYPE
        SYNTAX          DisplayString   (SIZE  (1..32))
        MAX-ACCESS      not-accessible
        STATUS          current
        DESCRIPTION
            "This object specifies a DHCP pool.
            The value must be same as an entry in esDhcpSPoolTable identified by
            esDhcpSPoolName."
        REFERENCE
            "esDhcpSPoolName is defined in DLINKES-DHCP-SERVER-MIB."
        ::= { esDhcpRPoolClassRelayTargetEntry 1 }

    esDhcpRPoClRelayTargetClassName OBJECT-TYPE
        SYNTAX          DisplayString   (SIZE  (1..32))
        MAX-ACCESS      not-accessible
        STATUS  current
        DESCRIPTION
            "This object specifies a DHCP class.
            The value must be same as an entry in esDhcpSClassTable identified by
            esDhcpSClassName."
        REFERENCE
            "esDhcpSClassName is defined in DLINKES-DHCP-SERVER-MIB."
        ::= { esDhcpRPoolClassRelayTargetEntry 2 }

    esDhcpRPoClRelayTargetAddr OBJECT-TYPE
        SYNTAX          IpAddress
        MAX-ACCESS      not-accessible
        STATUS          current
        DESCRIPTION
            "This object indicates the IP address of the target server for
            the class."
        ::= { esDhcpRPoolClassRelayTargetEntry 4 }


    esDhcpRPoClRelayTargetRowStatus OBJECT-TYPE
        SYNTAX          RowStatus
        MAX-ACCESS      read-create
        STATUS          current
        DESCRIPTION
            "This object manages this entry."
    ::= { esDhcpRPoolClassRelayTargetEntry 99 }

-- -----------------------------------------------------------------------------
    esDhcpRPoolRelayDestTable OBJECT-TYPE
        SYNTAX      SEQUENCE OF EsDhcpRPoolRelayDestEntry
        MAX-ACCESS  not-accessible
        STATUS      current
        DESCRIPTION
            "A table that contains DHCP relay destination IP address of DHCP
            pools."
        ::= { esDhcpRPoolObjects 2 }

    esDhcpRPoolRelayDestEntry OBJECT-TYPE
        SYNTAX      EsDhcpRPoolRelayDestEntry
        MAX-ACCESS  not-accessible
        STATUS      current
        DESCRIPTION
            "By using DHCP class, DHCP relay uses option configuration to further
            determine which IP addresses to allocate to clients."
        INDEX {
            esDhcpRPoolRelayDestPoolName,
            esDhcpRPoolRelayDestAddr}
       ::= { esDhcpRPoolRelayDestTable 1 }

    EsDhcpRPoolRelayDestEntry ::=     SEQUENCE {
        esDhcpRPoolRelayDestPoolName     DisplayString,
        esDhcpRPoolRelayDestAddr         IpAddress,
        esDhcpRPoolRelayDestRowStatus    RowStatus
    }

    esDhcpRPoolRelayDestPoolName OBJECT-TYPE
        SYNTAX          DisplayString (SIZE(1..32))
        MAX-ACCESS      not-accessible
        STATUS          current
        DESCRIPTION
            "This object specifies a DHCP pool.
            The value must be same as an entry in esDhcpSPoolTable identified by
            esDhcpSPoolName."
        REFERENCE
            "esDhcpSPoolName is defined in DLINKES-DHCP-SERVER-MIB."
        ::= { esDhcpRPoolRelayDestEntry 1 }


    esDhcpRPoolRelayDestAddr OBJECT-TYPE
        SYNTAX          IpAddress
        MAX-ACCESS      not-accessible
        STATUS          current
        DESCRIPTION
            "This object indicates the IP address of the relay destination for
            the pool."
        ::= { esDhcpRPoolRelayDestEntry 3 }

    esDhcpRPoolRelayDestRowStatus OBJECT-TYPE
        SYNTAX          RowStatus
        MAX-ACCESS      read-create
        STATUS          current
        DESCRIPTION
            "This object manages this entry."
    ::= { esDhcpRPoolRelayDestEntry 99 }

-- -----------------------------------------------------------------------------
    esDhcpRPoolRelaySourceTable OBJECT-TYPE
        SYNTAX          SEQUENCE OF EsDhcpRPoolRelaySourceEntry
        MAX-ACCESS      not-accessible
        STATUS          current
        DESCRIPTION
            "A table that contains the configuration of the source subnet that
            the client packets come from."
        ::= { esDhcpRPoolObjects 3 }

    esDhcpRPoolRelaySourceEntry OBJECT-TYPE
        SYNTAX          EsDhcpRPoolRelaySourceEntry
        MAX-ACCESS      not-accessible
        STATUS          current
        DESCRIPTION
            "An entry identifying a source subnet that the client packets come
            from."
        INDEX {
            esDhcpRPoolRelaySourcePoolName,
            esDhcpRPoolRelaySourceSubnet,
            esDhcpRPoolRelaySourceSubnetMask
        }
        ::= { esDhcpRPoolRelaySourceTable 1 }

    EsDhcpRPoolRelaySourceEntry ::=     SEQUENCE {
        esDhcpRPoolRelaySourcePoolName       DisplayString,
        esDhcpRPoolRelaySourceSubnet         IpAddress,
        esDhcpRPoolRelaySourceSubnetMask     IpAddress,
        esDhcpRPoolRelaySourceRowStatus      RowStatus
    }

    esDhcpRPoolRelaySourcePoolName OBJECT-TYPE
        SYNTAX          DisplayString (SIZE(1..32))
        MAX-ACCESS      not-accessible
        STATUS          current
        DESCRIPTION
            "This object specifies a DHCP pool.
            The value must be same as an entry in esDhcpSPoolTable identified by
            esDhcpSPoolName."
        REFERENCE
            "esDhcpSPoolName is defined in DLINKES-DHCP-SERVER-MIB."
        ::= { esDhcpRPoolRelaySourceEntry 1 }

    esDhcpRPoolRelaySourceSubnet OBJECT-TYPE
        SYNTAX          IpAddress
        MAX-ACCESS      not-accessible
        STATUS          current
        DESCRIPTION
            "This object indicates the source subnet of the client packets
            come from of the corresponding entry."
        ::= { esDhcpRPoolRelaySourceEntry 2 }

    esDhcpRPoolRelaySourceSubnetMask OBJECT-TYPE
        SYNTAX          IpAddress
        MAX-ACCESS      not-accessible
        STATUS          current
        DESCRIPTION
            "This object indicates the network mask of the source subnet
            for the corresponding entry."
        ::= { esDhcpRPoolRelaySourceEntry 3 }

    esDhcpRPoolRelaySourceRowStatus OBJECT-TYPE
        SYNTAX          RowStatus
        MAX-ACCESS      read-create
        STATUS          current
        DESCRIPTION
            "This object manages this entry."
        ::= { esDhcpRPoolRelaySourceEntry 99 }

-- -----------------------------------------------------------------------------
    esDhcpRelayIfObjects          OBJECT IDENTIFIER ::= { esDhcpRelayMIBObjects 3 }


-- -----------------------------------------------------------------------------
    esDhcpRIfAgentInfoChkTable OBJECT-TYPE
        SYNTAX          SEQUENCE OF EsDhcpRIfAgentInfoChkEntry
        MAX-ACCESS      not-accessible
        STATUS          current
        DESCRIPTION
            "A list of configurations about the DHCP relay validates the
            relay agent information (option 82) in the received DHCP reply packet
            on an interface.
            An entry is created/removed when checking option 82 is or not configured
            on an interface via CLI or by issuing appropriate sets to this table
            using snmp.
            If checking option 82 is not configured for an interface, the global
            setting, esDhcpRelayAgentInfoCheckEnabled takes effect. If checking
            option 82 is configured for an interface, the interface setting takes
            effect."
        ::= { esDhcpRelayIfObjects 2 }

    esDhcpRIfAgentInfoChkEntry OBJECT-TYPE
        SYNTAX          EsDhcpRIfAgentInfoChkEntry
        MAX-ACCESS      not-accessible
        STATUS          current
        DESCRIPTION
            "Defines an entry in the esDhcpRIfInfoChkTable."
        INDEX  { esDhcpRIfAgentInfoChkIfIndex }
        ::= { esDhcpRIfAgentInfoChkTable 1 }

    EsDhcpRIfAgentInfoChkEntry ::= SEQUENCE {
        esDhcpRIfAgentInfoChkIfIndex         InterfaceIndex,
        esDhcpRIfAgentInfoChkState           INTEGER
    }

    esDhcpRIfAgentInfoChkIfIndex OBJECT-TYPE
        SYNTAX          InterfaceIndex
        MAX-ACCESS      not-accessible
        STATUS          current
        DESCRIPTION
            "The ifIndex value of the interface.
             Only VLAN interfaces are valid interfaces for this object."
        ::= { esDhcpRIfAgentInfoChkEntry 1 }

    esDhcpRIfAgentInfoChkState OBJECT-TYPE
        SYNTAX          INTEGER{enabled(1), disabled(2), none(3)}
        MAX-ACCESS      read-create
        STATUS          current
        DESCRIPTION
            "This object indicates whether the DHCP relay agent validates the
             relay agent information option in the received DHCP reply packet
             on the corresponding interface."
        ::= { esDhcpRIfAgentInfoChkEntry 2 }

-- -----------------------------------------------------------------------------
    esDhcpRIfAgentInfoInsertTable OBJECT-TYPE
        SYNTAX          SEQUENCE OF EsDhcpRIfAgentInfoInsertEntry
        MAX-ACCESS      not-accessible
        STATUS          current
        DESCRIPTION
            "A list of configurations about whether insert option 82 for
            an interface during relay of DHCP request packets.
            An entry is created/removed when the insertion of
            option 82 is or not configured on an interface via CLI
            or by issuing appropriate sets to this table using snmp.
            If the insertion of option 82 is not configured for an interface,
            the global setting, esDhcpRelayAgentInfoInsertEnabled takes effect. If checking
            option 82 is configured for an interface, the interface setting takes
            effect."
        ::= { esDhcpRelayIfObjects 3 }

    esDhcpRIfAgentInfoInsertEntry OBJECT-TYPE
        SYNTAX          EsDhcpRIfAgentInfoInsertEntry
        MAX-ACCESS      not-accessible
        STATUS          current
        DESCRIPTION
            "Defines an entry in the esDhcpRIfAgentInfoInsertTable."
        INDEX  { esDhcpRIfAgentInfoInsertIfIndex }
        ::= { esDhcpRIfAgentInfoInsertTable 1 }

    EsDhcpRIfAgentInfoInsertEntry ::= SEQUENCE {
        esDhcpRIfAgentInfoInsertIfIndex         InterfaceIndex,
        esDhcpRIfAgentInfoInsertState           INTEGER
    }

    esDhcpRIfAgentInfoInsertIfIndex OBJECT-TYPE
        SYNTAX          InterfaceIndex
        MAX-ACCESS      not-accessible
        STATUS          current
        DESCRIPTION
            "The ifIndex value of the interface.
             Only VLAN interfaces are valid interfaces for this object."
        ::= { esDhcpRIfAgentInfoInsertEntry 1 }

    esDhcpRIfAgentInfoInsertState OBJECT-TYPE
        SYNTAX          INTEGER{enabled(1), disabled(2), none(3)}
        MAX-ACCESS      read-create
        STATUS          current
        DESCRIPTION
            "This object indicates whether insert option 82 for an interface
            during relay of DHCP request packets."
        ::= { esDhcpRIfAgentInfoInsertEntry 2 }

-- -----------------------------------------------------------------------------
    esDhcpRIfAgentInfoPolicyTable OBJECT-TYPE
        SYNTAX          SEQUENCE OF EsDhcpRIfAgentInfoPolicyEntry
        MAX-ACCESS      not-accessible
        STATUS          current
        DESCRIPTION
            "A list of configurations about relay agent information
            re-forwarding policy for the DHCP relay agent on an interface.
            An entry is created/removed when the re-forwarding policy
            is or not configured on an interface via CLI
            or by issuing appropriate sets to this table using snmp.
            If the re-forwarding policy is not configured for an interface,
            the global setting, esDhcpRelayAgentInfoPolicy takes effect. If
            re-forwarding policy is configured for an interface, the interface
            setting takes effect."
        ::= { esDhcpRelayIfObjects 4 }

    esDhcpRIfAgentInfoPolicyEntry OBJECT-TYPE
        SYNTAX          EsDhcpRIfAgentInfoPolicyEntry
        MAX-ACCESS      not-accessible
        STATUS          current
        DESCRIPTION
            "Defines an entry in the esDhcpRIfAgentInfoPolicyTable."
        INDEX  { esDhcpRIfAgentInfoPolicyIfIndex }
        ::= { esDhcpRIfAgentInfoPolicyTable 1 }

    EsDhcpRIfAgentInfoPolicyEntry ::= SEQUENCE {
        esDhcpRIfAgentInfoPolicyIfIndex         InterfaceIndex,
        esDhcpRIfAgentInfoPolicyAction          INTEGER
    }

    esDhcpRIfAgentInfoPolicyIfIndex OBJECT-TYPE
        SYNTAX          InterfaceIndex
        MAX-ACCESS      not-accessible
        STATUS          current
        DESCRIPTION
            "The ifIndex value of the interface.
             Only VLAN interfaces are valid interfaces for this object."
        ::= { esDhcpRIfAgentInfoPolicyEntry 1 }

    esDhcpRIfAgentInfoPolicyAction OBJECT-TYPE
        SYNTAX          INTEGER { drop(1), keep(2), replace(3), none(4)}
        MAX-ACCESS      read-write
        STATUS          current
        DESCRIPTION
            "This object indicates the re-forwarding policy of DHCP relay agent
             information option 82 for the corresponding interface.
             drop (1)    - discards the packet that already has the relay
                           option.
             keep (2)    - the DHCP requests packet that already has the relay
                           option is left unchanged and directly relayed to the
                           DHCP server.
             replace (3) - the DHCP requests packet that already has the relay
                           option will be replaced by a new option.
             none (4)    -  not configure the policy action on the interface. "
        ::= { esDhcpRIfAgentInfoPolicyEntry 2 }

-- -----------------------------------------------------------------------------
    esDhcpRIfAgentInfoTrustTable OBJECT-TYPE
        SYNTAX          SEQUENCE OF EsDhcpRIfAgentInfoTrustEntry
        MAX-ACCESS      not-accessible
        STATUS          current
        DESCRIPTION
            "A list of configurations about the relay agent trusts the relay
            information on an interface.
            An entry is created/removed when the trusting relay information
            is enabled/disabled on an interface via CLI or by issuing
            appropriate sets to this table using snmp.

            If esDhcpRelayInfoTrustAll is 'true', the dhcp relay information is
            trusted for all interfaces.  If esDhcpRelayInfoTrustAll is 'false',
            the trust state on an interface is determined whether
            the corresponding interface exists in this table. If exists, the
            corresponding interface is trusted, otherwise, the interface is not
            trusted.

            When relay information is trusted on an interface, the
            arriving packets with giaddr==0 (this relay agent is the first
            relay of this DHCP request packet) but with relay agent information
            option present will be accepted. If it is un-trusted, these packets
            will be dropped."
        ::= { esDhcpRelayIfObjects 5 }

    esDhcpRIfAgentInfoTrustEntry OBJECT-TYPE
        SYNTAX          EsDhcpRIfAgentInfoTrustEntry
        MAX-ACCESS      not-accessible
        STATUS          current
        DESCRIPTION
            "Defines an entry in the esDhcpRIfAgentInfoTrustTable."
        INDEX  { esDhcpRIfAgentInfoTrustIfIndex }
        ::= { esDhcpRIfAgentInfoTrustTable 1 }

    EsDhcpRIfAgentInfoTrustEntry ::= SEQUENCE {
        esDhcpRIfAgentInfoTrustIfIndex        InterfaceIndex,
        esDhcpRIfAgentInfoTrustEnabled        TruthValue
    }

    esDhcpRIfAgentInfoTrustIfIndex OBJECT-TYPE
        SYNTAX          InterfaceIndex
        MAX-ACCESS      not-accessible
        STATUS          current
        DESCRIPTION
            "The ifIndex value of the interface.
             Only VLAN interfaces are valid interfaces for this object."
        ::= { esDhcpRIfAgentInfoTrustEntry 1 }

    esDhcpRIfAgentInfoTrustEnabled OBJECT-TYPE
        SYNTAX          TruthValue
        MAX-ACCESS      read-write
        STATUS          current
        DESCRIPTION
            "This object indicates whether the interface is trusted on
            the not."
        ::= { esDhcpRIfAgentInfoTrustEntry 2 }


-- -----------------------------------------------------------------------------
    esDhcpRIfAgentInfoStateCtrlTable OBJECT-TYPE
        SYNTAX          SEQUENCE OF EsDhcpRIfAgentInfoStateCtrlEntry
        MAX-ACCESS      not-accessible
        STATUS          current
        DESCRIPTION
            "This table is used to manage the DHCP relay state for each port."
        ::= { esDhcpRelayIfObjects 7 }

    esDhcpRIfAgentInfoStateCtrlEntry OBJECT-TYPE
        SYNTAX          EsDhcpRIfAgentInfoStateCtrlEntry
        MAX-ACCESS      not-accessible
        STATUS          current
        DESCRIPTION
            "This object lists the current ports in the switch and their corresponding DHCP relay state."
        INDEX  { esDhcpRIfAgentInfoStateIfIndex }
        ::= { esDhcpRIfAgentInfoStateCtrlTable 1 }

    EsDhcpRIfAgentInfoStateCtrlEntry ::= SEQUENCE {
        esDhcpRIfAgentInfoStateIfIndex         InterfaceIndex,
        esDhcpRIfAgentInfoStateEnabled         TruthValue
    }

    esDhcpRIfAgentInfoStateIfIndex OBJECT-TYPE
        SYNTAX          InterfaceIndex
        MAX-ACCESS      not-accessible
        STATUS          current
        DESCRIPTION
            "This object indicates the module's port number.(1..Max port number in the module)."
        ::= { esDhcpRIfAgentInfoStateCtrlEntry 1 }

    esDhcpRIfAgentInfoStateEnabled OBJECT-TYPE
        SYNTAX          TruthValue
        MAX-ACCESS      read-write
        STATUS          current
        DESCRIPTION
            "This object indicates the state of the DHCP relay of each port."
        ::= { esDhcpRIfAgentInfoStateCtrlEntry 2 }

-- -----------------------------------------------------------------------------
    esDhcpRelayPortIfOption82Objects         OBJECT IDENTIFIER ::= { esDhcpRelayMIBObjects 4 }

    esDhcpRPortIfOp82RemIdTable OBJECT-TYPE
        SYNTAX SEQUENCE OF EsDhcpRPortIfOp82RemIdEntry
        MAX-ACCESS not-accessible
        STATUS current
        DESCRIPTION
            "This table is used to manage the remote ID sub-option of Option 82
            for physical port or port channel interface."
        ::={ esDhcpRelayPortIfOption82Objects 1}

    esDhcpRPortIfOp82RemIdEntry OBJECT-TYPE
        SYNTAX          EsDhcpRPortIfOp82RemIdEntry
        MAX-ACCESS      not-accessible
        STATUS current
        DESCRIPTION
            "An entry in esDhcpRPortIfOption82RemIdTable containing the
            configuration about the remote ID sub-option of Option 82 for the
            corresponding interface."
        INDEX { esDhcpRPortIfOp82RemIdIfIndex }
        ::={ esDhcpRPortIfOp82RemIdTable 1 }

    EsDhcpRPortIfOp82RemIdEntry ::=      SEQUENCE{
        esDhcpRPortIfOp82RemIdIfIndex       InterfaceIndex,
        esDhcpRPortIfOp82RemIdExpertUdfCfg  DisplayString
    }

    esDhcpRPortIfOp82RemIdIfIndex OBJECT-TYPE
        SYNTAX          InterfaceIndex
        MAX-ACCESS      not-accessible
        STATUS          current
        DESCRIPTION
            "This object indicates the ifIndex value of the port or port channel.
            Only physical port and port channel interface will appear in this
            table."
        ::= { esDhcpRPortIfOp82RemIdEntry 1 }

    esDhcpRPortIfOp82RemIdExpertUdfCfg OBJECT-TYPE
        SYNTAX          DisplayString  (SIZE  (0..32))
        MAX-ACCESS      read-write
        STATUS          current
        DESCRIPTION
            "This object indicates the per port/port channel bind an profile of flexible defined
             as remote ID.
            This object is used when esDhcpROption82RemoteIdType is set to
            'expertUdf'."
        ::= { esDhcpRPortIfOp82RemIdEntry 2 }

    esDhcpRPortIfOp82CirIdTable  OBJECT-TYPE
        SYNTAX          SEQUENCE OF EsDhcpRPortIfOp82CirIdEntry
        MAX-ACCESS      not-accessible
        STATUS          current
        DESCRIPTION
        "This table is used to manage the circuit ID sub-option of Option 82
            for physical port or port channel interface."
        ::={ esDhcpRelayPortIfOption82Objects 2}

    esDhcpRPortIfOp82CirIdEntry OBJECT-TYPE
        SYNTAX          EsDhcpRPortIfOp82CirIdEntry
        MAX-ACCESS      not-accessible
        STATUS          current
        DESCRIPTION
            "An entry in esDhcpRPortIfOp82CirIdTable containing the
            configuration about the circuit ID sub-option of Option 82 for the
            corresponding interface."
        INDEX { esDhcpRPortIfOp82CirIdIfIndex}
        ::={ esDhcpRPortIfOp82CirIdTable 1 }

    EsDhcpRPortIfOp82CirIdEntry ::=      SEQUENCE{
        esDhcpRPortIfOp82CirIdIfIndex         InterfaceIndex,
        esDhcpRPortIfOp82CirIdExpertUdfCfg    DisplayString
     }

    esDhcpRPortIfOp82CirIdIfIndex OBJECT-TYPE
        SYNTAX          InterfaceIndex
        MAX-ACCESS      not-accessible
        STATUS          current
        DESCRIPTION
            "This object indicates the ifIndex value of the port or port channel.
            Only physical port and port channel interface will appear in this
            table."
        ::= { esDhcpRPortIfOp82CirIdEntry 1 }

    esDhcpRPortIfOp82CirIdExpertUdfCfg OBJECT-TYPE
        SYNTAX          DisplayString  (SIZE  (0..32))
        MAX-ACCESS      read-write
        STATUS          current
        DESCRIPTION
            "This object indicates the per port/port channel bind an profile of flexible defined
             as circuit ID.
            This object is used when esDhcpROption82CircuitIdType is set to
            'expertUdf'."
        ::= { esDhcpRPortIfOp82CirIdEntry 2 }

-- -----------------------------------------------------------------------------
    esDhcpRelayVlanObjects          OBJECT IDENTIFIER ::= { esDhcpRelayMIBObjects 5 }

    esDhcpRVlanLocalRelayCtrlFirst2K  OBJECT-TYPE
        SYNTAX          Dlink2kVlanList
        MAX-ACCESS      read-write
        STATUS          current
        DESCRIPTION
            "This object specifies the DHCP Local Relay enabled VLAN in a
            string of octets containing one bit per VLAN for VLANs 1 to 2048.
            If the bit is set to '1', then the VLAN is enabled for DHCP Local Relay.
            "
        ::= { esDhcpRelayVlanObjects 1 }

    esDhcpRVlanLocalRelayCtrlSecond2K OBJECT-TYPE
        SYNTAX          Dlink2kVlanList
        MAX-ACCESS      read-write
        STATUS          current
        DESCRIPTION
            "This object specifies the DHCP Local Relay enabled VLAN in a
            string of octets containing one bit per VLAN for VLANs 2049 to 4094.
            If the bit is set to '1', then the VLAN is enabled for DHCP Local Relay.
            "
        ::= { esDhcpRelayVlanObjects 2 }


-- -----------------------------------------------------------------------------
    esDhcpRelayOption82ExpertUdfObjects          OBJECT IDENTIFIER ::= { esDhcpRelayMIBObjects 6 }

    esDhcpROption82ExUdfProfileTable OBJECT-TYPE
        SYNTAX          SEQUENCE OF EsDhcpROption82ExUdfProfileEntry
        MAX-ACCESS      not-accessible
        STATUS          current
        DESCRIPTION
            "A table that contains the configuration of the flexible user defined option82 format."
        ::= { esDhcpRelayOption82ExpertUdfObjects 1 }

    esDhcpROption82ExUdfProfileEntry OBJECT-TYPE
        SYNTAX          EsDhcpROption82ExUdfProfileEntry
        MAX-ACCESS      not-accessible
        STATUS          current
        DESCRIPTION
            "An entry identifying a profile that the flexible user defined option82 format ."
        INDEX {
            esDhcpROption82ExUdfProfileName
        }
        ::= { esDhcpROption82ExUdfProfileTable 1 }

    EsDhcpROption82ExUdfProfileEntry ::=     SEQUENCE {
        esDhcpROption82ExUdfProfileName      DisplayString,
        esDhcpROption82ExUdfProfileValue     DisplayString,
        esDhcpROption82ExUdfProfileRowStatus RowStatus
    }

    esDhcpROption82ExUdfProfileName OBJECT-TYPE
        SYNTAX          DisplayString (SIZE(1..32))
        MAX-ACCESS      not-accessible
        STATUS          current
        DESCRIPTION
            "The name of this profile entry. If the objects
             esDhcpROption82RemoteIdType or esDhcpROption82CircuitIdType
             set as expertUdf, the follow value fill in the profile name,
             and then the profile will bind with remote ID or circuit ID."
        ::= { esDhcpROption82ExUdfProfileEntry 1 }

    esDhcpROption82ExUdfProfileValue OBJECT-TYPE
        SYNTAX          DisplayString (SIZE(0..255))
        MAX-ACCESS      read-create
        STATUS          current
        DESCRIPTION
            "This object indicates the user defined format in circuit ID
             or remote ID. The particular format rules, please reference UIS."
        ::= { esDhcpROption82ExUdfProfileEntry 2 }

    esDhcpROption82ExUdfProfileRowStatus OBJECT-TYPE
        SYNTAX          RowStatus
        MAX-ACCESS      read-create
        STATUS          current
        DESCRIPTION
            "This object manages this entry."
        ::= { esDhcpROption82ExUdfProfileEntry 99}


     esDhcpROption82ExUdfMacFormatCase OBJECT-TYPE
        SYNTAX  INTEGER {
               uppercase(1),
               lowercase(2)
               }
        MAX-ACCESS  read-write
        STATUS  current
        DESCRIPTION
            "This object indicates the case format of the option82 MAC address for profile user define.
             It will be used in the object esDhcpROption82ExUdfProfileValue.

             uppercase: Using uppercase format, the formatted is: AA-BB-CC-DD-EE-FF.
             lowercase: Using lowercase format, the formatted is: aa-bb-cc-dd-ee-ff."
        ::= { esDhcpRelayOption82ExpertUdfObjects 2 }

     esDhcpROption82ExUdfMacFormatDelimiter OBJECT-TYPE
        SYNTAX  INTEGER {
               none(1),
               hyphen(2),
               colon(3),
               dot(4)
               }
        MAX-ACCESS  read-write
        STATUS  current
        DESCRIPTION
            "This object indicates the delimiter format of option82 MAC address for profile user define.
             It will be used in the object esDhcpROption82ExUdfProfileValue.

             none: Not using any delimiter, the format is: AABBCCDDEEFF
             hyphen: Using '-' as delimiter, the format is: AA-BB-CC-DD-EE-FF
             colon: Using ':' as delimiter, the format is: AA:BB:CC:DD:EE:FF
             dot: Using '.' as delimiter, the format is: AA.BB.CC.DD.EE.FF"
        ::= { esDhcpRelayOption82ExpertUdfObjects 3 }

     esDhcpROption82ExUdfMacFormatDelimiterNumber OBJECT-TYPE
        SYNTAX  INTEGER {
               oneDelimiterNumber(1),
               twoDelimiterNumber(2),
               fiveDelimiterNumber(5)
               }
        MAX-ACCESS  read-write
        STATUS  current
        DESCRIPTION
            "This object indicates the delimiter number of option82 MAC address for profile user define.
             It will be used in the object esDhcpROption82ExUdfProfileValue.

            oneDelimiterNumber: single delimiter, the format is: AABBCC.DDEEFF
            twoDelimiterNumber: double delimiter, the format is: AABB.CCDD.EEFF
            fiveDelimiterNumber: multiple delimiter, the format is: AA.BB.CC.DD.EE.FF
            Note: while esDhcpROption82ExUdfMacFormatDelimiter is none(1), the delimiter number will not take effect."
        ::= { esDhcpRelayOption82ExpertUdfObjects 4 }
-- -----------------------------------------------------------------------------

--  ***************************************************************************
--  Conformance
--  ***************************************************************************
    esDhcpRelayCompliances OBJECT IDENTIFIER ::= { esDhcpRelayMIBConformance 1 }

    esDhcpRelayCompliance MODULE-COMPLIANCE
        STATUS current
        DESCRIPTION
        "The compliance statement for entities which implement the
           DLINK-DHCP-RELAY-IPV4-MIB."
        MODULE -- this module
        MANDATORY-GROUPS {
            esDhcpRGblCfgGroup,
            esDhcpRPoolCfgGroup,
            esDhcpRInterfaceGroup2
        }

        GROUP       esDhcpROp82SuboptionGroup
        DESCRIPTION
            "This group is required only for implementations that support
            sub-options configuration of option 82."

        GROUP       esDhcpRVlanCfgGroup
        DESCRIPTION
            "This group is required only for implementations that support
            DHCP Local Relay for per VLAN."
        ::= { esDhcpRelayCompliances 1 }

    esDhcpRelayGroups OBJECT IDENTIFIER ::= { esDhcpRelayMIBConformance 2 }

    esDhcpRGblCfgGroup OBJECT-GROUP
        OBJECTS {
            esDhcpRelayAgentInfoCheckEnabled,
            esDhcpRelayAgentInfoInsertEnabled,
            esDhcpRelayAgentInfoPolicy,
            esDhcpRelayInfoTrustAll,
            esDhcpRelayUnicast
        }
        STATUS current
        DESCRIPTION
            "A collection of objects providing global configuration about DHCP
            relay."
        ::= { esDhcpRelayGroups 1 }


    esDhcpRPoolCfgGroup OBJECT-GROUP
        OBJECTS {
            esDhcpRPoClRelayTargetRowStatus,
            esDhcpRPoolRelayDestRowStatus,
            esDhcpRPoolRelaySourceRowStatus
        }
        STATUS current
        DESCRIPTION
           "A collection of objects providing DHCP pool configuration."
        ::= { esDhcpRelayGroups 2 }

    esDhcpROp82SuboptionGroup OBJECT-GROUP
        OBJECTS {
           esDhcpROption82RemoteIdType,
           esDhcpROption82RemoteIdUserDef,
           esDhcpROption82CircuitIdType,
           esDhcpROption82CircuitIdUserDef,
           esDhcpRPortIfOp82RemIdExpertUdfCfg,
           esDhcpRPortIfOp82CirIdExpertUdfCfg,
           esDhcpROption82ExUdfProfileValue,
           esDhcpROption82ExUdfProfileRowStatus,
           esDhcpROption82ExUdfMacFormatCase,
           esDhcpROption82ExUdfMacFormatDelimiter,
           esDhcpROption82ExUdfMacFormatDelimiterNumber
        }
        STATUS current
        DESCRIPTION
           "A collection of objects providing sub-options configuration of option 82."
        ::= { esDhcpRelayGroups 4 }

    esDhcpRVlanCfgGroup OBJECT-GROUP
        OBJECTS {
           esDhcpRVlanLocalRelayCtrlFirst2K,
           esDhcpRVlanLocalRelayCtrlSecond2K
        }
        STATUS current
        DESCRIPTION
            "A collection of objects which are used to configure as
            well as show information regarding the feature enabling
            on each VLAN."
        ::= { esDhcpRelayGroups 5 }

    esDhcpRInterfaceGroup2 OBJECT-GROUP
        OBJECTS {
            esDhcpRIfAgentInfoChkState,
            esDhcpRIfAgentInfoInsertState,
            esDhcpRIfAgentInfoPolicyAction,
            esDhcpRIfAgentInfoTrustEnabled,
            esDhcpRIfAgentInfoStateEnabled
        }
        STATUS current
        DESCRIPTION
            "A collection of objects providing per interface configuration of
            DHCP Relay."
        ::= { esDhcpRelayGroups 6 }

END
