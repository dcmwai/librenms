--  *****************************************************************
--  DLINKES-SFTP-SERVER-MIB.mib : Secure FTP Server MIB
--
--  Copyright (c) 2013 D-Link Corporation, all rights reserved.
--
--  *****************************************************************
DLINKES-SFTP-SERVER-MIB DEFINITIONS ::= BEGIN

    IMPORTS
        MODULE-IDENTITY,
        OBJECT-TYPE,
        Integer32,
        Unsigned32
                FROM SNMPv2-SMI
        TruthValue
                FROM SNMPv2-TC
        OBJECT-GROUP, MODULE-COMPLIANCE
                FROM SNMPv2-CONF
        dlinkCommon
                FROM DLINK-ID-REC-MIB;

    dlinkEsSftpServerMIB MODULE-IDENTITY
        LAST-UPDATED "201302180000Z"
        ORGANIZATION "D-Link Corp."
        CONTACT-INFO
            "        D-Link Corporation

             Postal: No. 289, Sinhu 3rd Rd., Neihu District,
                     Taipei City 114, Taiwan, R.O.C
             Tel:     +886-2-66000123
             E-mail: tsd@dlink.com.tw
            "
        DESCRIPTION
            "This MIB module defines objects for Secure Shell FTP Server."

        REVISION "201302180000Z"
        DESCRIPTION
            "This is the first version of the MIB file."

    ::= { dlinkCommon 152 }

-- -----------------------------------------------------------------------------
    esSftpServerNotifications    OBJECT IDENTIFIER ::= { dlinkEsSftpServerMIB 0 }
    esSftpServerObjects          OBJECT IDENTIFIER ::= { dlinkEsSftpServerMIB 1 }
    esSftpServerConformance      OBJECT IDENTIFIER ::= { dlinkEsSftpServerMIB 2 }

-- -----------------------------------------------------------------------------
    esSftpServerGeneral          OBJECT IDENTIFIER ::= { esSftpServerObjects 1 }

    esSftpServerEnabled OBJECT-TYPE
        SYNTAX          TruthValue
        MAX-ACCESS      read-write
        STATUS          current
        DESCRIPTION
            "This object indicates whether SFTP service is enabled or not."
        DEFVAL      { false }
        ::= { esSftpServerGeneral 1 }

    esSftpServerVersion OBJECT-TYPE
        SYNTAX          Unsigned32
        MAX-ACCESS      read-only
        STATUS          current
        DESCRIPTION
            "This object indicates the version of SFTP Server running on the
            switch.
            "
        ::= { esSftpServerGeneral 2 }

    esSftpServerTimeout OBJECT-TYPE
        SYNTAX          Integer32 (30..600)
        UNITS           "seconds"
        MAX-ACCESS      read-write
        STATUS          current
        DESCRIPTION
            "The idle timer for SFTP server.
            If there is no operation after the idle timer for an establised
            SFTP session, the switch will close this SFTP session actively."
        DEFVAL      { 120 }
        ::= { esSftpServerGeneral 3 }

-- Conformance


    esSftpServerCompliances  OBJECT IDENTIFIER ::= { esSftpServerConformance 1 }
    esSftpServerGroups       OBJECT IDENTIFIER ::= { esSftpServerConformance 2 }


    esSftpServerMIBCompliance MODULE-COMPLIANCE
        STATUS   current
        DESCRIPTION
            "The compliance statement for entities which
            implement the DLINKES-SFTP-SERVER-MIB."
        MODULE MANDATORY-GROUPS {
            esSftpServerConfigGroup,
            esSftpServerInfoGroup
        }

        ::= { esSftpServerCompliances 1 }

    esSftpServerConfigGroup OBJECT-GROUP
        OBJECTS             {
            esSftpServerEnabled,
            esSftpServerTimeout
        }
        STATUS current
        DESCRIPTION
            "A collection of objects provides configuration for SFTP Server."
        ::= { esSftpServerGroups 1 }

    esSftpServerInfoGroup OBJECT-GROUP
        OBJECTS             {
            esSftpServerVersion
        }
        STATUS current
        DESCRIPTION
            "A collection of objects provides information for SFTP Server."
        ::= { esSftpServerGroups 2 }

END
