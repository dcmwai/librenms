--  *****************************************************************
--  DLINKES-ERROR-DISABLE-MIB.mib : Error Disable MIB
-- 
--  Copyright (c) 2013 D-Link Corporation, all rights reserved.
--   
--  *****************************************************************

DLINKES-ERROR-DISABLE-MIB DEFINITIONS ::= BEGIN


    IMPORTS
        MODULE-IDENTITY,
        OBJECT-TYPE,
        NOTIFICATION-TYPE,
        Integer32,
        Unsigned32
                FROM SNMPv2-SMI     
        TEXTUAL-CONVENTION,
        TruthValue
                FROM SNMPv2-TC  
        MODULE-COMPLIANCE, OBJECT-GROUP, NOTIFICATION-GROUP
		        FROM SNMPv2-CONF       
        InterfaceIndex
                FROM IF-MIB
        VlanId,
        VlanIdOrNone
                FROM Q-BRIDGE-MIB                 
        dlinkCommon			
				FROM DLINK-ID-REC-MIB;


    dlinkEsErrDisableMIB MODULE-IDENTITY
        LAST-UPDATED "201307080000Z"
        ORGANIZATION "D-Link Corp."
        CONTACT-INFO
            "         D-Link Corporation
             Postal: No. 289, Sinhu 3rd Rd., Neihu District,
                     Taipei City 114, Taiwan, R.O.C
             Tel:    +886-2-66000123
             E-mail: tsd@dlink.com.tw
            "
        DESCRIPTION
            "This MIB module defines objects for error disabled."
        REVISION "201305020000Z"
        DESCRIPTION
            "This is the first version of the MIB file."           

        REVISION "201307080000Z" 
        DESCRIPTION
            "Modified the object esErrDisIfStatusDisReason to
            esErrDisIfStatusDisReasonIndex, make this object to be the third
            index of esErrDisIfStatusEntry, to display more than one reason on
            a port or vlan interface if more than one reason is recocovering
            on the port or vlan interface."

        REVISION "201404110000Z" 
        DESCRIPTION
            "Add scheduledShutdown and scheduledHibernation into EsErrDisReasonID.
	    Modify description of esErrDisIfStatusTimeLeft, using 0xFFFFFFFF to
	    indicates no automatic recovery."
	    
	REVISION "201502070000Z" 
        DESCRIPTION
            "Add duld into EsErrDisReasonID."
	    
    ::= { dlinkCommon 45 }
    
--
-- Textual conventions
--    

    EsErrDisReasonID ::= TEXTUAL-CONVENTION
        STATUS          current
        DESCRIPTION
            "An integer-value assigned to various conditions
            that can error disable a system entity.
            loopbackDetect:  Loopback Detection
            l2ptGuard: L2 Protocol Tunneling. 
            psecureViolation: Port Security violation.
            stormControl: (broadcast/multicast/unicast)storm control. 
            bpduProtect: BPDU protected. 
            arpRateLimit: ARP rate limit.
            dhcpRateLimit: DHCP rate limit.
            ddm: Digital Diagnostics Monitoring
            scheduledShutdown: Scheduled Port-shutdown by Power Saving
            scheduledHibernation:Scheduled Hibernation by Power Saving
            duld:D-LINK Unidirectional Link Detection
            "
        SYNTAX  INTEGER  
            {   loopbackDetect(1), 
                l2ptGuard(2), 
                psecureViolation(3), 
                stormControl(4), 
                bpduProtect(5), 
                arpRateLimit(6),
                dhcpRateLimit(7),
                ddm(8),
                scheduledShutdown(9),
                scheduledHibernation(10),
                duld(11)
            }
-- -----------------------------------------------------------------------------
    esErrDisableMIBNotifications     OBJECT IDENTIFIER ::= { dlinkEsErrDisableMIB 0 }
    esErrDisableMIBObjects           OBJECT IDENTIFIER ::= { dlinkEsErrDisableMIB 1 }
    esErrDisableMIBConformance       OBJECT IDENTIFIER ::= { dlinkEsErrDisableMIB 2 }

-- -----------------------------------------------------------------------------
    esErrDisRecoveryTable OBJECT-TYPE
        SYNTAX          SEQUENCE OF EsErrDisRecoveryEntry
        MAX-ACCESS      not-accessible
        STATUS          current
        DESCRIPTION            
            "This table contains the recovery mechanism for the features with 
            error-disable functionality.
            Transceiver monitoring module (the EsErrDisReasonID is 'ddm') can also
            put a SFP port which is in abnormal status in error disabled state. 
            This error disable cannot be auto recovered but can only be manually
            recovered. As a result, there is no entry for error cause is 'ddm'
            in this table. 
            "
        ::= { esErrDisableMIBObjects 1 }

    esErrDisRecoveryEntry OBJECT-TYPE
        SYNTAX          EsErrDisRecoveryEntry
        MAX-ACCESS      not-accessible
        STATUS          current
        DESCRIPTION            
            "An entry is created for each feature which has error-disable 
             functionality."
        INDEX    { esErrDisRecoveryIndex }
        ::= { esErrDisRecoveryTable 1 }

    EsErrDisRecoveryEntry ::= SEQUENCE {
        esErrDisRecoveryIndex        EsErrDisReasonID,
        esErrDisRecoveryEnable       TruthValue,
        esErrDisRecoveryInterval     Integer32
    }

    esErrDisRecoveryIndex OBJECT-TYPE
        SYNTAX          EsErrDisReasonID
        MAX-ACCESS      not-accessible
        STATUS          current
        DESCRIPTION
            "This object indicates the cause of error-disable.
             An integer-value assigned to various conditions
             that can error disable a system entity.
             loopbackDetect(1)       - The error-disable reason is Loopback Detection. 
             l2ptGuard(2)            - The error-disable reason is L2 Protocol Tunneling. 
             psecureViolation(3)     - The error-disable reason is Port Security violation. 
             stormControl(4)         - The error-disable reason is (broadcast/multicast/unicast)storm control.  
             bpduProtect(5)          - The error-disable reason is BPDU protected. 
             arpRateLimit(6)         - The error-disable reason is ARP rate limit.
             dhcpRateLimit(7)        - The error-disable reason is DHCP rate limit.
             ddm(8)                  - The error-disable reason is Digital Diagnostics Monitoring.
             scheduledShutdown(9)    - The error-disable reason is Scheduled Port-shutdown by Power Saving.
             scheduledHibernation(10)- The error-disable reason is Scheduled Hibernation by Power Saving.
             duld(11)                - The error-disable reason is D-LINK Unidirectional Link Detection."
        ::= { esErrDisRecoveryEntry 1 }

    esErrDisRecoveryEnable OBJECT-TYPE
        SYNTAX          TruthValue
        MAX-ACCESS      read-write
        STATUS          current
        DESCRIPTION           
            "This object specifies whether the system can
            automatically recover a system entity that has been
            disabled by the cause."
        DEFVAL      { false }
        ::= { esErrDisRecoveryEntry 2 }

    esErrDisRecoveryInterval OBJECT-TYPE
        SYNTAX          Integer32 (5..86400)
        UNITS           "seconds"
        MAX-ACCESS      read-write
        STATUS          current
        DESCRIPTION
            "Specifies the error-recovery time interval on specific cause 
            to recover the port/interface from the error disabled situation."
        DEFVAL      { 300 }
        ::= { esErrDisRecoveryEntry 3 }

-- -----------------------------------------------------------------------------
    esErrDisIfStatusTableNum  OBJECT-TYPE
        SYNTAX          Unsigned32
        MAX-ACCESS      read-only
        STATUS          current
        DESCRIPTION
            "Indicates the number of entries present in the esErrDisIfStatusTable."
        ::= { esErrDisableMIBObjects 2 }

    esErrDisIfStatusTable OBJECT-TYPE
        SYNTAX          SEQUENCE OF EsErrDisIfStatusEntry
        MAX-ACCESS      not-accessible
        STATUS          current
        DESCRIPTION
             "This table provides next recovery timeout information about an interface 
             disabled by a feature."           
        ::= { esErrDisableMIBObjects 3 }

    esErrDisIfStatusEntry OBJECT-TYPE
        SYNTAX          EsErrDisIfStatusEntry
        MAX-ACCESS      not-accessible
        STATUS          current
        DESCRIPTION
            "An entry indicates next recovery timeout information about an interface 
            or (interface, vlan) disabled by a feature."    
        INDEX    
            {   esErrDisIfStatusIfIndex,
                esErrDisIfStatusVlanIndex,
                esErrDisIfStatusDisReasonIndex }
        ::= { esErrDisIfStatusTable 1 }

    EsErrDisIfStatusEntry ::= SEQUENCE {
        esErrDisIfStatusIfIndex      InterfaceIndex,
        esErrDisIfStatusVlanIndex    VlanIdOrNone,
        esErrDisIfStatusDisReasonIndex   EsErrDisReasonID,
        esErrDisIfStatusTimeLeft     Unsigned32
    }

    esErrDisIfStatusIfIndex OBJECT-TYPE
        SYNTAX          InterfaceIndex
        MAX-ACCESS      not-accessible
        STATUS          current
        DESCRIPTION           
            "This object is the interface index of the interface disabled by a feature."
        ::= { esErrDisIfStatusEntry 1 }

    esErrDisIfStatusVlanIndex OBJECT-TYPE
        SYNTAX          VlanIdOrNone
        MAX-ACCESS      not-accessible
        STATUS          current
        DESCRIPTION                      
            "This object indicates the VLAN in the given interface
            that has been error-disabled. If the physical interface is
            error-disabled then the value of this object is 0." 
        ::= { esErrDisIfStatusEntry 2 }
        
    esErrDisIfStatusDisReasonIndex OBJECT-TYPE
        SYNTAX          EsErrDisReasonID
        MAX-ACCESS      not-accessible
        STATUS          current
        DESCRIPTION
           "This object indicates the reason which cause the interface disabled."
        ::= { esErrDisIfStatusEntry 3 }

    esErrDisIfStatusTimeLeft OBJECT-TYPE
        SYNTAX          Unsigned32
        UNITS           "seconds"
        MAX-ACCESS      read-only
        STATUS          current
        DESCRIPTION
            "This object indicates the time left that the interface will be 
            automatically recovered. Value 0xFFFFFFFF indicates the interface
	    won't be automatically recovered."
        ::= { esErrDisIfStatusEntry 4 }

-- -----------------------------------------------------------------------------             
     esErrDisNotificationEnable OBJECT-TYPE
        SYNTAX          BITS {
            errDisableAsserted(0),
            errDisableCleared(1)            
        }
        MAX-ACCESS  read-write
        STATUS      current
        DESCRIPTION
         "This object indicates whether a specified notification is enabled or not.
         If a bit corresponding to a notification is set to 1, then 
         the specified notification can be generated.

         errDisableAsserted(0) - Controls the notifications for a port/vlan
                            entering into error disabled state.

         errDisableCleared(1) - Controls the notifications for a port/vlan 
                            exiting from error disabled state. 
            
         "
    ::= { esErrDisableMIBObjects 4 }   
    
    esErrDisNotifRate OBJECT-TYPE
        SYNTAX        Unsigned32 (0..1000)
        UNITS         "notifications per minute"
        MAX-ACCESS    read-write
        STATUS        current
        DESCRIPTION   
            "Expressed in the number of notifications can be generated 
            per minute. 
            This object configures the rate-limit of  SNMP Notification for
            errDisable feature. 
            A value of 0 indicates that an SNMP Notification is generated
            for every error disabled event."        
        DEFVAL      { 0 }              
        ::= { esErrDisableMIBObjects 5 }
        
-- -----------------------------------------------------------------------------         
    esErrDisNotifyInfo        OBJECT IDENTIFIER ::= { esErrDisableMIBObjects 6 }
   
    esErrDisNotifyInfoPortIfIndex OBJECT-TYPE
        SYNTAX          InterfaceIndex 
        MAX-ACCESS      accessible-for-notify
        STATUS          current
        DESCRIPTION
            "This object indicates the port number of error disabled port."
        ::= { esErrDisNotifyInfo 1 }    
        
    esErrDisNotifyInfoLoopDetectedVID OBJECT-TYPE
        SYNTAX          VlanId 
        MAX-ACCESS      accessible-for-notify
        STATUS          current
        DESCRIPTION
            "This object indicates the VLAN ID that has detected a loopback."
        ::= { esErrDisNotifyInfo 2 }

    esErrDisNotifyInfoReasonID OBJECT-TYPE
        SYNTAX          EsErrDisReasonID
        MAX-ACCESS      accessible-for-notify
        STATUS          current
        DESCRIPTION
            "This object indicates the condition which cause a port/vlan enter
            into error disabled state."
        ::= { esErrDisNotifyInfo 3 }               
        
--  ***************************************************************************	
--  Notifications
--  ***************************************************************************                                
    esErrDisNotifyPortDisabledAssert  NOTIFICATION-TYPE
        OBJECTS   {
            esErrDisNotifyInfoPortIfIndex,
            esErrDisNotifyInfoReasonID
        }
        STATUS  current
        DESCRIPTION
               "The trap is sent when a port enters into error disabled state."
        ::= { esErrDisableMIBNotifications 1 }

    esErrDisNotifyPortDisabledClear  NOTIFICATION-TYPE
        OBJECTS {
            esErrDisNotifyInfoPortIfIndex,
            esErrDisNotifyInfoReasonID
        }
        STATUS  current
        DESCRIPTION
              "The trap is sent when a port loop restarts after the interval time."
        ::= { esErrDisableMIBNotifications 2 }

    esErrDisNotifyVlanDisabledAssert  NOTIFICATION-TYPE
        OBJECTS   {
            esErrDisNotifyInfoPortIfIndex,
            esErrDisNotifyInfoReasonID,
            esErrDisNotifyInfoLoopDetectedVID
        }
        STATUS  current
        DESCRIPTION
               "The trap is sent when a Port with a VID loop occurs."
        ::= { esErrDisableMIBNotifications 3 }

    esErrDisNotifyVlanDisabledClear NOTIFICATION-TYPE
        OBJECTS  {
            esErrDisNotifyInfoPortIfIndex,
            esErrDisNotifyInfoReasonID,
            esErrDisNotifyInfoLoopDetectedVID
        }
        STATUS  current
        DESCRIPTION
               "The trap is sent when a Port with a VID restarts after the interval time."
        ::= { esErrDisableMIBNotifications 4 }
                
--  ***************************************************************************	
--  Conformance
--  ***************************************************************************
    esErrDisMIBCompliances  OBJECT IDENTIFIER
        ::= { esErrDisableMIBConformance 1 }

    esErrDisMIBGroups  OBJECT IDENTIFIER
        ::= { esErrDisableMIBConformance 2 } 
    
    esErrDisMIBCompliance MODULE-COMPLIANCE
        STATUS          current
        DESCRIPTION
            "The compliance statement for entities which implement the 
			DLINKES-ERROR-DISABLE-MIB."
        MODULE          -- this module
        MANDATORY-GROUPS 
            {   esErrDisRecoveryCfgGroup,
                esErrDisIfStatusGroup,
                esErrDisNotifyCfgGroup,
                esErrDisNotificationGroup
            }
        ::= { esErrDisMIBCompliances 1 }

    esErrDisRecoveryCfgGroup OBJECT-GROUP
		OBJECTS 
		    {   esErrDisRecoveryEnable, 
		        esErrDisRecoveryInterval 
		    }
		STATUS current
		DESCRIPTION 
			"A collection of objects to configure the error recovery of the 
			error-disable feature."
		::= { esErrDisMIBGroups 1 }
		
    esErrDisIfStatusGroup OBJECT-GROUP
		OBJECTS 
		    {   esErrDisIfStatusTableNum, 
		        esErrDisIfStatusTimeLeft 
		    }
		STATUS current
		DESCRIPTION 
			"A collection of objects which indicate error-disable interface 
			status."
		::= { esErrDisMIBGroups 2 }
    
    esErrDisNotifyCfgGroup OBJECT-GROUP
		OBJECTS 
		    {   esErrDisNotificationEnable, 
		        esErrDisNotifRate,
		        esErrDisNotifyInfoPortIfIndex, 
		        esErrDisNotifyInfoReasonID,
		        esErrDisNotifyInfoLoopDetectedVID
		    }
		STATUS current
		DESCRIPTION 
			"A collection of objects to configure the error recovery of the 
			error-disable feature."
		::= { esErrDisMIBGroups 3 }
		
    esErrDisNotificationGroup NOTIFICATION-GROUP
        NOTIFICATIONS { 
            esErrDisNotifyPortDisabledAssert,
            esErrDisNotifyPortDisabledClear,
            esErrDisNotifyVlanDisabledAssert,
            esErrDisNotifyVlanDisabledClear
        }
        STATUS current
        DESCRIPTION
            "The collection of notifications used for monitoring ErrDisable status"
        ::= { esErrDisMIBGroups 4 }   

END
