--  *****************************************************************
--  DLINKES-DHCP6-SERVER-MIB.mib : DHCPv6 Server MIB
--
--  Copyright (c) 2013 D-Link Corporation, all rights reserved.
--
--  *****************************************************************

DLINKES-DHCP6-SERVER-MIB DEFINITIONS ::= BEGIN

    IMPORTS
        MODULE-IDENTITY,
        OBJECT-TYPE,
        Integer32,
        Unsigned32,
        IpAddress
            FROM SNMPv2-SMI
        DisplayString,
        RowStatus,
        TruthValue,
        DateAndTime
                FROM SNMPv2-TC
        MODULE-COMPLIANCE,
	    OBJECT-GROUP
		    FROM SNMPv2-CONF
        InterfaceIndex
            FROM IF-MIB
        InetAddressPrefixLength, InetAddressIPv6
            FROM INET-ADDRESS-MIB
        dlinkCommon
			FROM DLINK-ID-REC-MIB;


    dlinkEsDhcp6ServerMIB MODULE-IDENTITY
        LAST-UPDATED "201310090000Z"
        ORGANIZATION "D-Link Corp."
        CONTACT-INFO
            "        D-Link Corporation
             Postal: No. 289, Sinhu 3rd Rd., Neihu District,
             Taipei City 114, Taiwan, R.O.C
             Tel:     +886-2-66000123
             E-mail: tsd@dlink.com.tw
            "
        DESCRIPTION
            "This MIB module defines objects for DHCPv6 Server."

        REVISION "201709210000Z"
        DESCRIPTION
            "Remove 'esDhcp6SCfgChanged' from esDhcp6ServGeneral.
            "

        REVISION "201301180000Z"
        DESCRIPTION
            "This is the first version of the MIB file for 'DHCPv6 Server'
             functionality.
            "

        REVISION "201310090000Z"
        DESCRIPTION
             "modify node esDhcp6SBindExpire syntax to DateAndTime."
        ::= { dlinkCommon 223 }

-- -----------------------------------------------------------------------------
    esDhcp6ServerMIBNotifications    OBJECT IDENTIFIER ::= { dlinkEsDhcp6ServerMIB 0 }
    esDhcp6ServerMIBObjects          OBJECT IDENTIFIER ::= { dlinkEsDhcp6ServerMIB 1 }
    esDhcp6ServerMIBConformance      OBJECT IDENTIFIER ::= { dlinkEsDhcp6ServerMIB 2 }

-- -----------------------------------------------------------------------------
    esDhcp6ServGeneral          OBJECT IDENTIFIER ::= { esDhcp6ServerMIBObjects 1}

    esDhcp6ServiceEnabled OBJECT-TYPE
        SYNTAX          TruthValue
        MAX-ACCESS      read-write
        STATUS          current
        DESCRIPTION
            "This object enables/disables the DHCPv6 server and relay service on
            the device."
        DEFVAL          { false }
        ::= { esDhcp6ServGeneral 1 }

    esDhcp6SExcludedAddressTable OBJECT-TYPE
        SYNTAX          SEQUENCE OF EsDhcp6SExcludedAddressEntry
        MAX-ACCESS      not-accessible
        STATUS      current
        DESCRIPTION
            "A list of configurations about a range of IPv6 addresses that
            the DHCPv6 server should not assign to DHCPv6 client."
        ::= { esDhcp6ServGeneral 2 }

    esDhcp6SExcludedAddressEntry OBJECT-TYPE
        SYNTAX          EsDhcp6SExcludedAddressEntry
        MAX-ACCESS      not-accessible
        STATUS          current
        DESCRIPTION
            "An entry contans information about an IP address range
            that the DHCPv6 server should not assign to DHCPv6 client."
        INDEX {
            esDhcp6SExcludedAddressBeginAddr,
            esDhcp6SExcludedAddressEndAddr
        }
    ::= { esDhcp6SExcludedAddressTable 1 }

    EsDhcp6SExcludedAddressEntry ::=      SEQUENCE {
        esDhcp6SExcludedAddressBeginAddr          InetAddressIPv6,
        esDhcp6SExcludedAddressEndAddr            InetAddressIPv6,
        esDhcp6SExcludedAddressRowStatus          RowStatus
    }

    esDhcp6SExcludedAddressBeginAddr OBJECT-TYPE
        SYNTAX          InetAddressIPv6
        MAX-ACCESS      not-accessible
        STATUS          current
        DESCRIPTION
            "This object indicates the first IPv6 address of this excluded
            address range."
        ::= { esDhcp6SExcludedAddressEntry 1 }

    esDhcp6SExcludedAddressEndAddr OBJECT-TYPE
        SYNTAX          InetAddressIPv6
        MAX-ACCESS      not-accessible
        STATUS          current
        DESCRIPTION
            "This object indicates the last IPv6 address of this excluded
            address range."
        ::= { esDhcp6SExcludedAddressEntry 2 }

    esDhcp6SExcludedAddressRowStatus OBJECT-TYPE
        SYNTAX          RowStatus
        MAX-ACCESS      read-create
        STATUS          current
        DESCRIPTION
            "The status of this conceptual row."
        ::= { esDhcp6SExcludedAddressEntry 3 }


    esDhcp6SLocalPoolTable OBJECT-TYPE
        SYNTAX          SEQUENCE OF EsDhcp6SLocalPoolEntry
        MAX-ACCESS      not-accessible
        STATUS      current
        DESCRIPTION
            "A list of configurations contains information for local IPv6
            prefix pools."
        ::= { esDhcp6ServGeneral 3 }

    esDhcp6SLocalPoolEntry OBJECT-TYPE
        SYNTAX          EsDhcp6SLocalPoolEntry
        MAX-ACCESS      not-accessible
        STATUS          current
        DESCRIPTION
            "An entry contains information about a local IPv6 prefix pool
            that will be assigned to DHCPv6 client."
        INDEX { esDhcp6SLocalPoolName }
        ::= { esDhcp6SLocalPoolTable 1 }

    EsDhcp6SLocalPoolEntry ::=      SEQUENCE {
        esDhcp6SLocalPoolName                DisplayString,
        esDhcp6SLocalPoolPrefix              InetAddressIPv6,
        esDhcp6SLocalPoolPrefixLen           InetAddressPrefixLength,
        esDhcp6SLocalPoolPrefixAssignLen     InetAddressPrefixLength,
        esDhcp6SLocalPoolFreeAddrNum         Unsigned32,
        esDhcp6SLocalPoolInUseAddrNum        Unsigned32,
        esDhcp6SLocalPoolRowStatus           RowStatus
    }

    esDhcp6SLocalPoolName OBJECT-TYPE
        SYNTAX          DisplayString (SIZE(1..32))
        MAX-ACCESS      not-accessible
        STATUS          current
        DESCRIPTION
            "The name of this local IPv6 prefix pool."
        ::= { esDhcp6SLocalPoolEntry 1 }

    esDhcp6SLocalPoolPrefix OBJECT-TYPE
        SYNTAX          InetAddressIPv6
        MAX-ACCESS      read-create
        STATUS          current
        DESCRIPTION
            "This object indicates the IPv6 prefix address of the local pool."
        ::= { esDhcp6SLocalPoolEntry 2 }

    esDhcp6SLocalPoolPrefixLen OBJECT-TYPE
        SYNTAX          InetAddressPrefixLength
        MAX-ACCESS      read-create
        STATUS          current
        DESCRIPTION
            "This object indicates the IPv6 prefix length in bits of the local pool."
        ::= { esDhcp6SLocalPoolEntry 3 }

    esDhcp6SLocalPoolPrefixAssignLen OBJECT-TYPE
        SYNTAX          InetAddressPrefixLength
        MAX-ACCESS      read-create
        STATUS          current
        DESCRIPTION
            "This object indicates the prefix length in bits to delegate to DHCPv6
            client from the pool. The value of esDhcp6SLocalPoolPrefixAssignLen
            cannot be less than the value of esDhcp6SLocalPoolPrefixLen.
            "
        ::= { esDhcp6SLocalPoolEntry 4 }

    esDhcp6SLocalPoolFreeAddrNum OBJECT-TYPE
        SYNTAX          Unsigned32
        MAX-ACCESS      read-only
        STATUS          current
        DESCRIPTION
            "This object indicates the number of prefixes which are available to
            be allocated."
        ::= { esDhcp6SLocalPoolEntry 5 }

    esDhcp6SLocalPoolInUseAddrNum OBJECT-TYPE
        SYNTAX          Unsigned32
        MAX-ACCESS      read-only
        STATUS          current
        DESCRIPTION
            "This object indicates the number of already allocated prefixes."
        ::= { esDhcp6SLocalPoolEntry 6 }

    esDhcp6SLocalPoolRowStatus OBJECT-TYPE
        SYNTAX          RowStatus
        MAX-ACCESS      read-create
        STATUS          current
        DESCRIPTION
            "The status of this conceptual row."
        ::= { esDhcp6SLocalPoolEntry 7 }

-- --------------------------------------------------------------------

    esDhcp6ServPoolMgmt         OBJECT IDENTIFIER ::= { esDhcp6ServerMIBObjects 2}

    esDhcp6SPoolTable OBJECT-TYPE
        SYNTAX          SEQUENCE OF EsDhcp6SPoolEntry
        MAX-ACCESS      not-accessible
        STATUS          current
        DESCRIPTION
             "A table of DHCPv6 pool Information."
        ::= { esDhcp6ServPoolMgmt 1 }

    esDhcp6SPoolEntry OBJECT-TYPE
        SYNTAX      EsDhcp6SPoolEntry
        MAX-ACCESS  not-accessible
        STATUS      current
        DESCRIPTION
            "Defines an entry in the esDhcp6SPoolTable."
        INDEX  { esDhcp6SPoolName }
        ::= { esDhcp6SPoolTable 1 }

    EsDhcp6SPoolEntry ::= SEQUENCE {
            esDhcp6SPoolName         DisplayString,
            esDhcp6SPoolRowStatus    RowStatus
        }

    esDhcp6SPoolName OBJECT-TYPE
        SYNTAX          DisplayString (SIZE(1..32))
        MAX-ACCESS      not-accessible
        STATUS          current
        DESCRIPTION
            "The name of this pool."
        ::= { esDhcp6SPoolEntry 1 }

    esDhcp6SPoolRowStatus OBJECT-TYPE
        SYNTAX          RowStatus
        MAX-ACCESS      read-create
        STATUS          current
        DESCRIPTION
            "The row status variable, used according to installation
             and removal conventions for conceptual rows."
        ::= { esDhcp6SPoolEntry 2 }

-- --------------------------------------------------------------------
    esDhcp6SPoolDomainNameTable OBJECT-TYPE
        SYNTAX          SEQUENCE OF EsDhcp6SPoolDomainNameEntry
        MAX-ACCESS      not-accessible
        STATUS          current
        DESCRIPTION
             "A table of domain name information in DHCPv6 pools."
        ::= { esDhcp6ServPoolMgmt 2 }

    esDhcp6SPoolDomainNameEntry OBJECT-TYPE
        SYNTAX          EsDhcp6SPoolDomainNameEntry
        MAX-ACCESS      not-accessible
        STATUS          current
        DESCRIPTION
            "Defines an entry in the esDhcp6SPoolDomainNameTable.
            The first instance identifier index value identifies the
            esDhcp6SPoolEntry that a domain name (esDhcp6SPoolDomainNameEntry)
            belongs to. An entry is removed from this table when its
            corresponding esDhcp6SPoolEntry is deleted."
        INDEX  {
            esDhcp6SPoolName,
            esDhcp6SPoolDomainNameAdminIndex
        }
        ::= { esDhcp6SPoolDomainNameTable 1 }

    EsDhcp6SPoolDomainNameEntry ::= SEQUENCE {
        esDhcp6SPoolDomainNameAdminIndex		Unsigned32,
        esDhcp6SPoolDomainName               DisplayString,
        dhcp6ServerDomainNameRowStatus      RowStatus
    }

    esDhcp6SPoolDomainNameAdminIndex OBJECT-TYPE
        SYNTAX          Unsigned32 (1..8)
        MAX-ACCESS      not-accessible
        STATUS          current
        DESCRIPTION
            "This object indicates the order of preference of a domain name
            in a DHCPv6 pool. The number of domain name can be specified in a
            DHCPv6 pool is project dependent."
        ::= { esDhcp6SPoolDomainNameEntry 1 }

    esDhcp6SPoolDomainName OBJECT-TYPE
        SYNTAX          DisplayString (SIZE(1..32))
        MAX-ACCESS      read-create
        STATUS          current
        DESCRIPTION
            "The domain name of the corresponding entry."
        ::= { esDhcp6SPoolDomainNameEntry 2 }

    dhcp6ServerDomainNameRowStatus OBJECT-TYPE
        SYNTAX      RowStatus
        MAX-ACCESS  read-create
        STATUS      current
        DESCRIPTION
            "The row status variable, used according to installation
             and removal conventions for conceptual rows."
        ::= { esDhcp6SPoolDomainNameEntry 3 }

-- -----------------------------------------------------------------------------
    esDhcp6SPoolDnsServerTable OBJECT-TYPE
        SYNTAX          SEQUENCE OF EsDhcp6SPoolDnsServerEntry
        MAX-ACCESS      not-accessible
        STATUS          current
        DESCRIPTION
            "A list of DNS server configurations for DHCPv6 pools."
        ::= { esDhcp6ServPoolMgmt 3 }

    esDhcp6SPoolDnsServerEntry OBJECT-TYPE
        SYNTAX          EsDhcp6SPoolDnsServerEntry
        MAX-ACCESS      not-accessible
        STATUS          current
        DESCRIPTION
            "An entry contains DNS server configuration in a DHCPv6 pool.
            The first instance identifier index value identifies the
            esDhcp6SPoolEntry that a DNS server (esDhcp6SPoolDnsServerEntry)
            belongs to. An entry is removed from this table when its
            corresponding esDhcp6SPoolEntry is deleted."
        INDEX {
            esDhcp6SPoolName,
            esDhcp6SPoolDnsServerIndex
        }
        ::= { esDhcp6SPoolDnsServerTable 1 }

    EsDhcp6SPoolDnsServerEntry ::=    SEQUENCE {
        esDhcp6SPoolDnsServerIndex		Unsigned32,
        esDhcp6SPoolDnsServerAddr    	InetAddressIPv6,
        esDhcp6SPoolDnsServerRowStatus   RowStatus
    }

    esDhcp6SPoolDnsServerIndex OBJECT-TYPE
        SYNTAX          Unsigned32 (1..8)
        MAX-ACCESS      not-accessible
        STATUS          current
        DESCRIPTION
            "This objects indicates the order of preference of a DNS server in a
            DHCPv6 pool."
        ::= { esDhcp6SPoolDnsServerEntry 1 }

    esDhcp6SPoolDnsServerAddr OBJECT-TYPE
        SYNTAX          InetAddressIPv6
        MAX-ACCESS      read-create
        STATUS          current
        DESCRIPTION
           "The IPv6 address of the DNS server."
        ::= { esDhcp6SPoolDnsServerEntry 2 }

    esDhcp6SPoolDnsServerRowStatus OBJECT-TYPE
        SYNTAX          RowStatus
        MAX-ACCESS      read-create
        STATUS          current
        DESCRIPTION
            "The status of this conceptual row."
        ::= { esDhcp6SPoolDnsServerEntry 3}

-- -----------------------------------------------------------------------------
    esDhcp6SPoolAddrPrefixTable OBJECT-TYPE
        SYNTAX          SEQUENCE OF EsDhcp6SPoolAddrPrefixEntry
        MAX-ACCESS      not-accessible
        STATUS          current
        DESCRIPTION
             "A table of address prefix information in DHCPv6 pools."
        ::= { esDhcp6ServPoolMgmt 4 }

    esDhcp6SPoolAddrPrefixEntry OBJECT-TYPE
        SYNTAX          EsDhcp6SPoolAddrPrefixEntry
        MAX-ACCESS      not-accessible
        STATUS          current
        DESCRIPTION
            "Defines an entry in the esDhcp6SPoolAddrPrefixTable.
            The first instance identifier index value identifies the
            esDhcp6SPoolEntry that a address-prefix (esDhcp6SPoolAddrPrefixEntry)
            belongs to. An entry is removed from this table when its
            corresponding esDhcp6SPoolEntry is deleted. "
        INDEX  {  esDhcp6SPoolName }
        ::= { esDhcp6SPoolAddrPrefixTable 1 }

    EsDhcp6SPoolAddrPrefixEntry ::= SEQUENCE {
        esDhcp6SPoolAddrPrefixAddr  		    InetAddressIPv6,
        esDhcp6SPoolAddrPrefixLength         InetAddressPrefixLength,
        esDhcp6SPoolAddrPrefixVLtime         Unsigned32,
        esDhcp6SPoolAddrPrefixPLtime         Unsigned32,
        esDhcp6SPoolAddrPrefixRowStatus      RowStatus
    }

    esDhcp6SPoolAddrPrefixAddr OBJECT-TYPE
        SYNTAX          InetAddressIPv6
        MAX-ACCESS      read-create
        STATUS          current
        DESCRIPTION
            "This object indicates IPv6 address prefix to be assigned to client."
        ::= { esDhcp6SPoolAddrPrefixEntry 1 }

    esDhcp6SPoolAddrPrefixLength OBJECT-TYPE
        SYNTAX          InetAddressPrefixLength
        MAX-ACCESS      read-create
        STATUS          current
        DESCRIPTION
            "This object indicates the length in bits of the address prefix."
        ::= { esDhcp6SPoolAddrPrefixEntry 2 }

    esDhcp6SPoolAddrPrefixVLtime OBJECT-TYPE
        SYNTAX          Unsigned32 (60 .. 4294967295)
        UNITS           "seconds"
        MAX-ACCESS      read-create
        STATUS          current
        DESCRIPTION
            "The valid lifetime of the address prefix in seconds."
        DEFVAL      { 2592000 }
        ::= { esDhcp6SPoolAddrPrefixEntry 3 }

    esDhcp6SPoolAddrPrefixPLtime OBJECT-TYPE
        SYNTAX          Unsigned32 (60 .. 4294967295)
        UNITS           "seconds"
        MAX-ACCESS      read-create
        STATUS          current
        DESCRIPTION
            "The preferred lifetime of the address prefix in seconds."
        DEFVAL      { 604800  }
        ::= { esDhcp6SPoolAddrPrefixEntry 4 }

    esDhcp6SPoolAddrPrefixRowStatus OBJECT-TYPE
        SYNTAX          RowStatus
        MAX-ACCESS      read-create
        STATUS          current
        DESCRIPTION
            "The row status variable, used according to installation
             and removal conventions for conceptual rows."
        ::= { esDhcp6SPoolAddrPrefixEntry 5 }

-- -----------------------------------------------------------------------------
    esDhcp6SPoolAddrAssignTable OBJECT-TYPE
        SYNTAX          SEQUENCE OF EsDhcp6SPoolAddrAssignEntry
        MAX-ACCESS      not-accessible
        STATUS          current
        DESCRIPTION
             "A table of address assignment information in DHCPv6 pools."
        ::= { esDhcp6ServPoolMgmt 6 }

    esDhcp6SPoolAddrAssignEntry OBJECT-TYPE
        SYNTAX          EsDhcp6SPoolAddrAssignEntry
        MAX-ACCESS      not-accessible
        STATUS          current
        DESCRIPTION
            "Defines an entry in the esDhcp6SPoolAddrAssignTable.
            The first instance identifier index value identifies the
            esDhcp6SPoolEntry that an address-assignment (esDhcp6SPoolAddrAssignEntry)
            belongs to. An entry is removed from this table when its
            corresponding esDhcp6SPoolEntry is deleted.
            "
        INDEX  {
            esDhcp6SPoolName,
            esDhcp6SPoolAddrAssignAddr
        }
        ::= { esDhcp6SPoolAddrAssignTable 1 }

    EsDhcp6SPoolAddrAssignEntry ::= SEQUENCE {
        esDhcp6SPoolAddrAssignAddr  		       InetAddressIPv6,
        esDhcp6SPoolAddrAssignLength            InetAddressPrefixLength,
        esDhcp6SPoolAddrAssignClientDuid        DisplayString,
        esDhcp6SPoolAddrAssignSetIaid           TruthValue,
        esDhcp6SPoolAddrAssignIaid              DisplayString,
        esDhcp6SPoolAddrAssignVLtime            Unsigned32,
        esDhcp6SPoolAddrAssignPLtime            Unsigned32,
        esDhcp6SPoolAddrAssignRowStatus         RowStatus
    }

    esDhcp6SPoolAddrAssignAddr OBJECT-TYPE
        SYNTAX          InetAddressIPv6
        MAX-ACCESS      read-create
        STATUS          current
        DESCRIPTION
            "This object indicates the IPv6 address to be assigned to client."
        ::= { esDhcp6SPoolAddrAssignEntry 1 }

    esDhcp6SPoolAddrAssignLength OBJECT-TYPE
        SYNTAX          InetAddressPrefixLength
        MAX-ACCESS      read-create
        STATUS          current
        DESCRIPTION
            "This object indicates the length in bits of the address."
        ::= { esDhcp6SPoolAddrAssignEntry 2 }

    esDhcp6SPoolAddrAssignClientDuid OBJECT-TYPE
        SYNTAX          DisplayString	(SIZE(1..28))
        MAX-ACCESS      read-create
        STATUS          current
        DESCRIPTION
            "This object indicates the DHCP unique identifier (DUID) of
            the client to get the address."
        ::= { esDhcp6SPoolAddrAssignEntry 3 }

    esDhcp6SPoolAddrAssignSetIaid OBJECT-TYPE
        SYNTAX          TruthValue
        MAX-ACCESS      read-create
        STATUS          current
        DESCRIPTION
            "This object indicates whether esDhcp6SPoolAddrAssignIaid is set or not."
        DEFVAL      { false }
        ::= { esDhcp6SPoolAddrAssignEntry 4 }

    esDhcp6SPoolAddrAssignIaid OBJECT-TYPE
        SYNTAX          DisplayString	(SIZE(1..8))
        MAX-ACCESS      read-create
        STATUS          current
        DESCRIPTION
            "This object indicates the Identity association identifier (IAID) of the
            entry. The value of esDhcp6SPoolAddrAssignIaid uniquely identifies a
            collection of non-temporary addresses (IA_NA) assigned on the client.
            esDhcp6SPoolAddrAssignIaid is only valid when esDhcp6SPoolAddrAssignSetIaid
            is 'true'."
        ::= { esDhcp6SPoolAddrAssignEntry 5 }

    esDhcp6SPoolAddrAssignVLtime OBJECT-TYPE
        SYNTAX          Unsigned32
        MAX-ACCESS      read-create
        STATUS          current
        DESCRIPTION
            "This object indicates valid lifetime of the assigned address in seconds.
            The valid lifetime should be greater than preferred lifetime."
        DEFVAL      { 2592000 }
        ::= { esDhcp6SPoolAddrAssignEntry 6 }

    esDhcp6SPoolAddrAssignPLtime OBJECT-TYPE
        SYNTAX          Unsigned32 (60 .. 4294967295)
        MAX-ACCESS      read-create
        STATUS          current
        DESCRIPTION
            "This object indicates preferred lifetime of the assigned address in seconds.
            The valid lifetime should be greater than preferred lifetime."
        DEFVAL      { 604800 }
        ::= { esDhcp6SPoolAddrAssignEntry 7 }

    esDhcp6SPoolAddrAssignRowStatus OBJECT-TYPE
        SYNTAX          RowStatus
        MAX-ACCESS      read-create
        STATUS          current
        DESCRIPTION
            "The row status variable, used according to installation
             and removal conventions for conceptual rows."
        ::= { esDhcp6SPoolAddrAssignEntry 8 }

-- -----------------------------------------------------------------------------
    esDhcp6SPoolPdTable OBJECT-TYPE
        SYNTAX          SEQUENCE OF EsDhcp6SPoolPdEntry
        MAX-ACCESS      not-accessible
        STATUS          current
        DESCRIPTION
             "A table of prefix delegation information in DHCPv6 pools."
        ::= { esDhcp6ServPoolMgmt 7 }

    esDhcp6SPoolPdEntry OBJECT-TYPE
        SYNTAX          EsDhcp6SPoolPdEntry
        MAX-ACCESS      not-accessible
        STATUS          current
        DESCRIPTION
            "Defines an entry in the esDhcp6SPoolPdTable.
            The first instance identifier index value identifies the
            esDhcp6SPoolEntry that a prefix delegation (esDhcp6SPoolPdEntry)
            belongs to. An entry is removed from this table when its
            corresponding esDhcp6SPoolEntry is deleted.
            "
        INDEX  {
            esDhcp6SPoolName,
            esDhcp6SPoolPdPrefix,
            esDhcp6SPoolPdPrefixLength
        }
        ::= { esDhcp6SPoolPdTable 1 }

    EsDhcp6SPoolPdEntry ::= SEQUENCE {
        esDhcp6SPoolPdPrefix     		InetAddressIPv6,
        esDhcp6SPoolPdPrefixLength       InetAddressPrefixLength,
        esDhcp6SPoolPdClientDuid         DisplayString,
        esDhcp6SPoolPdSetIaid            TruthValue,
        esDhcp6SPoolPdIaid               DisplayString,
        esDhcp6SPoolPdVLtime             Unsigned32,
        esDhcp6SPoolPdPLtime             Unsigned32,
        esDhcp6SPoolPdRowStatus          RowStatus
    }

    esDhcp6SPoolPdPrefix OBJECT-TYPE
        SYNTAX          InetAddressIPv6
        MAX-ACCESS      read-create
        STATUS          current
        DESCRIPTION
            "This object indicates IPv6 prefix to be delegated to client."
        ::= { esDhcp6SPoolPdEntry 1 }

    esDhcp6SPoolPdPrefixLength OBJECT-TYPE
        SYNTAX          InetAddressPrefixLength
        MAX-ACCESS      read-create
        STATUS          current
        DESCRIPTION
            "This object indicates the length in bits of the prefix."
        ::= { esDhcp6SPoolPdEntry 2 }

    esDhcp6SPoolPdClientDuid OBJECT-TYPE
        SYNTAX          DisplayString	(SIZE(1..28))
        MAX-ACCESS      read-create
        STATUS          current
        DESCRIPTION
            "This object indicates the DHCP unique identifier (DUID) of
            the client to get the address."
        ::= { esDhcp6SPoolPdEntry 3 }

    esDhcp6SPoolPdSetIaid OBJECT-TYPE
        SYNTAX          TruthValue
        MAX-ACCESS      read-create
        STATUS          current
        DESCRIPTION
            "This object indicates whether esDhcp6SPoolPdIaid is set or not."
        DEFVAL      { false }
        ::= { esDhcp6SPoolPdEntry 4 }

    esDhcp6SPoolPdIaid OBJECT-TYPE
        SYNTAX          DisplayString	(SIZE(1..8))
        MAX-ACCESS      read-create
        STATUS          current
        DESCRIPTION
            "This object indicates the Identity association identifier (IAID) of the
            entry. The value of esDhcp6SPoolPdIaid uniquely identifies a
            collection of prefixes assigned to the requesting router.
            esDhcp6SPoolPdIaid is only valid when esDhcp6SPoolAddrAssignSetIaid
            is 'true'."
        ::= { esDhcp6SPoolPdEntry 5 }

    esDhcp6SPoolPdVLtime OBJECT-TYPE
        SYNTAX          Unsigned32 (60 .. 4294967295)
        MAX-ACCESS      read-create
        STATUS          current
        DESCRIPTION
            "This object indicates valid lifetime of the allocated prefix in seconds.
            The valid lifetime should be greater than preferred lifetime."
         DEFVAL      { 2592000 }
        ::= { esDhcp6SPoolPdEntry 6 }

    esDhcp6SPoolPdPLtime OBJECT-TYPE
        SYNTAX          Unsigned32 (60 .. 4294967295)
        MAX-ACCESS      read-create
        STATUS          current
        DESCRIPTION
            "This object indicates preferred lifetime of the address in seconds.
            The preferred lifetime should be less than valid lifetime."
         DEFVAL      { 604800  }
        ::= { esDhcp6SPoolPdEntry 7 }

    esDhcp6SPoolPdRowStatus OBJECT-TYPE
        SYNTAX          RowStatus
        MAX-ACCESS      read-create
        STATUS          current
        DESCRIPTION
            "The row status variable, used according to installation
             and removal conventions for conceptual rows."
        ::= { esDhcp6SPoolPdEntry 8 }

-- -----------------------------------------------------------------------------
    esDhcp6SPoolPdLocPoolTable OBJECT-TYPE
        SYNTAX          SEQUENCE OF EsDhcp6SPoolPdLocPoolEntry
        MAX-ACCESS      not-accessible
        STATUS          current
        DESCRIPTION
             "A table of local prefix pool association in DHCPv6 pools."
        ::= { esDhcp6ServPoolMgmt 8 }

    esDhcp6SPoolPdLocPoolEntry OBJECT-TYPE
        SYNTAX          EsDhcp6SPoolPdLocPoolEntry
        MAX-ACCESS      not-accessible
        STATUS          current
        DESCRIPTION
            "Defines an entry in the esDhcp6SPoolPdLocPoolTable.
            The first instance identifier index value identifies the
            esDhcp6SPoolEntry that a local prefix pool association (esDhcp6SPoolPdLocPoolEntry)
            belongs to. An entry is removed from this table when its
            corresponding esDhcp6SPoolEntry is deleted.
            "
        INDEX  {  esDhcp6SPoolName }
        ::= { esDhcp6SPoolPdLocPoolTable 1 }

    EsDhcp6SPoolPdLocPoolEntry ::= SEQUENCE {
        esDhcp6SPoolPdLocPoolName           DisplayString,
        esDhcp6SPoolPdLocPoolVLtime         Unsigned32,
        esDhcp6SPoolPdLocPoolPLtime         Unsigned32,
        esDhcp6SPoolPdLocPoolRowStatus      RowStatus
    }

    esDhcp6SPoolPdLocPoolName OBJECT-TYPE
        SYNTAX          DisplayString (SIZE(1..32))
        MAX-ACCESS      read-create
        STATUS          current
        DESCRIPTION
            "The name of the associated local IPv6 prefix pool."
        ::= { esDhcp6SPoolPdLocPoolEntry 1 }

    esDhcp6SPoolPdLocPoolVLtime OBJECT-TYPE
        SYNTAX          Unsigned32 (60 .. 4294967295)
        MAX-ACCESS      read-create
        STATUS          current
        DESCRIPTION
            "This object indicates valid lifetime for the delegated prefix in
            seconds. The valid lifetime should be greater than preferred lifetime."
         DEFVAL      { 2592000 }
        ::= { esDhcp6SPoolPdLocPoolEntry 2 }

    esDhcp6SPoolPdLocPoolPLtime OBJECT-TYPE
        SYNTAX          Unsigned32 (60 .. 4294967295)
        MAX-ACCESS      read-create
        STATUS          current
        DESCRIPTION
            "This object indicates preferred lifetime for the delegated prefix in
            seconds. The preferred lifetime should be less than valid lifetime."
         DEFVAL      { 604800  }
        ::= { esDhcp6SPoolPdLocPoolEntry 3 }

    esDhcp6SPoolPdLocPoolRowStatus OBJECT-TYPE
        SYNTAX          RowStatus
        MAX-ACCESS      read-create
        STATUS          current
        DESCRIPTION
            "The row status variable, used according to installation
             and removal conventions for conceptual rows."
        ::= { esDhcp6SPoolPdLocPoolEntry 4 }

-- -----------------------------------------------------------------------------
    esDhcp6ServIfMgmt         OBJECT IDENTIFIER ::= { esDhcp6ServerMIBObjects 3}

    esDhcp6ServIfTable OBJECT-TYPE
        SYNTAX          SEQUENCE OF EsDhcp6ServIfEntry
        MAX-ACCESS      not-accessible
        STATUS          current
        DESCRIPTION
             "A table contains interface-specific DHCPv6 server service
             configuration.
             An entry is created/removed when DHCPv6 server service is
             specified/unspecified.
             When DHCPv6 server service is specified on an interface means
             DHCPv6 server feature is enabled on that interface.
             "
        ::= { esDhcp6ServIfMgmt 1 }

    esDhcp6ServIfEntry OBJECT-TYPE
        SYNTAX          EsDhcp6ServIfEntry
        MAX-ACCESS      not-accessible
        STATUS          current
        DESCRIPTION
            "Defines an entry in the esDhcp6ServIfTable."
        INDEX  { esDhcp6ServIfIndex }
        ::= { esDhcp6ServIfTable 1 }

    EsDhcp6ServIfEntry ::= SEQUENCE {
            esDhcp6ServIfIndex           InterfaceIndex,
            esDhcp6ServIfPoolName        DisplayString,
            esDhcp6ServIfRapidCommit     TruthValue,
            esDhcp6ServIfAllowHint       TruthValue,
            esDhcp6ServIfPreference      Unsigned32,
            esDhcp6ServIfRowStatus       RowStatus
        }

    esDhcp6ServIfIndex OBJECT-TYPE
        SYNTAX          InterfaceIndex
        MAX-ACCESS      not-accessible
        STATUS          current
        DESCRIPTION
            "The ifIndex value of the interface.
             Only VLAN interfaces are valid interfaces."
        ::= { esDhcp6ServIfEntry 1 }

    esDhcp6ServIfPoolName OBJECT-TYPE
        SYNTAX          DisplayString (SIZE (1..32))
        MAX-ACCESS      read-create
        STATUS          current
        DESCRIPTION
            "This object indicates the name of the DHCPv6 pool used to serve
            the request received on the interface."
        ::= { esDhcp6ServIfEntry 2 }

    esDhcp6ServIfRapidCommit OBJECT-TYPE
        SYNTAX          TruthValue
        MAX-ACCESS      read-create
        STATUS          current
        DESCRIPTION
            "This object indicates whether allow proceeding of two-message
            exchange."
        DEFVAL      { false }
        ::= { esDhcp6ServIfEntry 3 }

    esDhcp6ServIfAllowHint OBJECT-TYPE
        SYNTAX          TruthValue
        MAX-ACCESS      read-create
        STATUS          current
        DESCRIPTION
            "This object indicates whether delegate the prefix based on the
            prefix hint by the client. By default, the prefix hint by client is
            ignored."
        DEFVAL      { false }
        ::= { esDhcp6ServIfEntry 4 }

    esDhcp6ServIfPreference OBJECT-TYPE
        SYNTAX          Unsigned32 (0..255)
        MAX-ACCESS      read-create
        STATUS          current
        DESCRIPTION
            "This object indicates the preference value to be advertised by the
            server. The larger value indicates the higher priority."
        DEFVAL      { 0 }
        ::= { esDhcp6ServIfEntry 5 }

    esDhcp6ServIfRowStatus OBJECT-TYPE
        SYNTAX          RowStatus
        MAX-ACCESS      read-create
        STATUS          current
        DESCRIPTION
            "The row status variable, used according to installation
             and removal conventions for conceptual rows."
        ::= { esDhcp6ServIfEntry 6 }

-- -----------------------------------------------------------------------------
    esDhcp6ServInfo          OBJECT IDENTIFIER ::= { esDhcp6ServerMIBObjects 4}

    esDhcp6SBindingTable OBJECT-TYPE
        SYNTAX          SEQUENCE OF EsDhcp6SBindingEntry
        MAX-ACCESS      not-accessible
        STATUS          current
        DESCRIPTION
             "A table contains DHCPv6 binding information."
        ::= { esDhcp6ServInfo 1 }

    esDhcp6SBindingEntry OBJECT-TYPE
        SYNTAX          EsDhcp6SBindingEntry
        MAX-ACCESS      not-accessible
        STATUS          current
        DESCRIPTION
            "Defines an entry in the esDhcp6SBindingTable."
        INDEX  {
            esDhcp6SBindIfIndex,
            esDhcp6SBindClientDuid,
            esDhcp6SBindIaType,
            esDhcp6SBindIaId,
            esDhcp6SBindAddrOrPrefix,
            esDhcp6SBindAddrOrPrefixLen
        }
        ::= { esDhcp6SBindingTable 1 }

    EsDhcp6SBindingEntry ::= SEQUENCE {
            esDhcp6SBindIfIndex              InterfaceIndex,
            esDhcp6SBindClientDuid           OCTET STRING,
            esDhcp6SBindIaType               INTEGER,
            esDhcp6SBindIaId                 Unsigned32,
            esDhcp6SBindAddrOrPrefix         InetAddressIPv6,
            esDhcp6SBindAddrOrPrefixLen      InetAddressPrefixLength,
            esDhcp6SBindClientLinkLocalAddr  InetAddressIPv6,
            esDhcp6SBindIaT1                 Unsigned32,
            esDhcp6SBindIaT2                 Unsigned32,
            esDhcp6SBindVLtime               Unsigned32,
            esDhcp6SBindPLtime               Unsigned32,
            esDhcp6SBindExpire               DateAndTime,
            esDhcp6SBindClear       		    INTEGER
        }

    esDhcp6SBindIfIndex OBJECT-TYPE
        SYNTAX          InterfaceIndex
        MAX-ACCESS      not-accessible
        STATUS          current
        DESCRIPTION
            "The ifIndex of the VLAN interface on which the binding is located."
        ::= { esDhcp6SBindingEntry 1 }

    esDhcp6SBindClientDuid OBJECT-TYPE
        SYNTAX          OCTET STRING
        MAX-ACCESS      not-accessible
        STATUS          current
        DESCRIPTION
            "This object indicates the DHCP unique identifier (DUID) of
            the client."
        ::= { esDhcp6SBindingEntry 2 }

    esDhcp6SBindIaType OBJECT-TYPE
        SYNTAX          INTEGER  {
            other(0),
            iapd(1),
            iana(2)
        }
        MAX-ACCESS      not-accessible
        STATUS          current
        DESCRIPTION
            "The type of binding IA (Identity association).
            other(0) - The other types not specified here.
            iapd(1)  - Prefix Delegation
            iana(2)  - Non-temporary Addresses
            "
        ::= { esDhcp6SBindingEntry 3 }

     esDhcp6SBindIaId OBJECT-TYPE
        SYNTAX          Unsigned32 (60 .. 4294967295)
        MAX-ACCESS      not-accessible
        STATUS          current
        DESCRIPTION
            "This object indicates the Identity association identifier (IAID) of the
            entry. "
        ::= { esDhcp6SBindingEntry 4 }

    esDhcp6SBindAddrOrPrefix OBJECT-TYPE
        SYNTAX          InetAddressIPv6
        MAX-ACCESS      not-accessible
        STATUS          current
        DESCRIPTION
            "This object indicates the IPv6 address or prefix allocated to the client."
        ::= { esDhcp6SBindingEntry 5 }

    esDhcp6SBindAddrOrPrefixLen OBJECT-TYPE
        SYNTAX          InetAddressPrefixLength
        MAX-ACCESS      not-accessible
        STATUS          current
        DESCRIPTION
            "This object indicates the length in bits of the IPv6 address or
            prefix allocated/delegated to the client."
        ::= { esDhcp6SBindingEntry 6 }

    esDhcp6SBindClientLinkLocalAddr OBJECT-TYPE
        SYNTAX          InetAddressIPv6
        MAX-ACCESS      read-only
        STATUS          current
        DESCRIPTION
            "This object indicates the IPv6 link local address or prefix
            allocated/delegated to the client."
        ::= { esDhcp6SBindingEntry 7 }

    esDhcp6SBindIaT1 OBJECT-TYPE
        SYNTAX          Unsigned32
        MAX-ACCESS      read-only
        STATUS          current
        DESCRIPTION
            "This object indicates T1 of the IA. At time T1 for an IA, the
            client initiates a Renew/Reply message exchange to extend the
            lifetimes on any addresses in the IA."
        ::= { esDhcp6SBindingEntry 8 }

    esDhcp6SBindIaT2 OBJECT-TYPE
        SYNTAX          Unsigned32
        MAX-ACCESS      read-only
        STATUS          current
        DESCRIPTION
            "This object indicates T2 of the IA.
            At time T2 for an IA, the client initiates a Rebind/Reply message
            exchange with any available server."
        ::= { esDhcp6SBindingEntry 9 }

    esDhcp6SBindVLtime OBJECT-TYPE
        SYNTAX          Unsigned32
        MAX-ACCESS      read-only
        STATUS          current
        DESCRIPTION
            "This object indicates valid lifetime for the binding in seconds."
        ::= { esDhcp6SBindingEntry 10 }

    esDhcp6SBindPLtime OBJECT-TYPE
        SYNTAX          Unsigned32
        MAX-ACCESS      read-only
        STATUS          current
        DESCRIPTION
            "This object indicates preferred lifetime for the binding in seconds."
        ::= { esDhcp6SBindingEntry 11 }

    esDhcp6SBindExpire OBJECT-TYPE
        SYNTAX          DateAndTime
        MAX-ACCESS      read-only
        STATUS          current
        DESCRIPTION
            "This object indicates the expiration of the binding entry.
		    The special value of all '00'Hs indicates that the binding will never
		    be expired (infinite)."
        ::= { esDhcp6SBindingEntry 12 }

    esDhcp6SBindClear  OBJECT-TYPE
   		SYNTAX      INTEGER	{
   		    clear(1),
			noOp(2)
		}
		MAX-ACCESS  read-write
		STATUS current
		DESCRIPTION
			"This object is used to clear the binding entry when
			set to 'clear'.
			No action is taken if this object is set to 'noOp'.
			When read, the value 'noOp' is returned."
		::= { esDhcp6SBindingEntry 13 }

--  ***************************************************************************
--  Conformance
--  ***************************************************************************
	esDhcp6ServerCompliances OBJECT IDENTIFIER ::= { esDhcp6ServerMIBConformance 1 }

	esDhcp6ServerCompliance MODULE-COMPLIANCE
		STATUS current
		DESCRIPTION
			"The compliance statement for entities which implement the
			DLINKES-DHCP6-SERVER-MIB."
		MODULE -- this module
		MANDATORY-GROUPS {
		    esDhcp6SGblCfgGroup,
		    esDhcp6SLocalPoolGroup,
		    esDhcp6SPoolGroup,
		    esDhcp6SInterfaceGroup,
		    esDhcp6SNonTempAddrAssignGroup,
		    esDhcp6SInfoGroup
		}

		GROUP       esDhcp6SPrefixDelegationGroup
           DESCRIPTION
              "This group is required only if the Prefix-Delegation feature
              is implemented by the agent."

		::= { esDhcp6ServerCompliances 1 }

	esDhcp6ServerGroups OBJECT IDENTIFIER ::= { esDhcp6ServerMIBConformance 2 }

	esDhcp6SGblCfgGroup OBJECT-GROUP
		OBJECTS {
			esDhcp6ServiceEnabled,
			esDhcp6SExcludedAddressRowStatus
		}
		STATUS current
		DESCRIPTION
			"A collection of objects providing global configuration about DHCPv6
			server."
		::= { esDhcp6ServerGroups 1 }

	esDhcp6SLocalPoolGroup OBJECT-GROUP
		OBJECTS {
		    esDhcp6SLocalPoolPrefix,
		    esDhcp6SLocalPoolPrefixLen,
		    esDhcp6SLocalPoolPrefixAssignLen,
		    esDhcp6SLocalPoolRowStatus
		}
		STATUS current
		DESCRIPTION
			"A collection of objects providing DHCP class configuration."
		::= { esDhcp6ServerGroups 2 }

	esDhcp6SPoolGroup OBJECT-GROUP
		OBJECTS {
		    esDhcp6SPoolRowStatus,
		    esDhcp6SPoolDomainName,
		    dhcp6ServerDomainNameRowStatus,
		    esDhcp6SPoolDnsServerAddr,
		    esDhcp6SPoolDnsServerRowStatus
		}
		STATUS current
		DESCRIPTION
			"A collection of objects providing DHCP relay agent configuration
			of a class or address range of a class under a DHCP pool."
		::= { esDhcp6ServerGroups 3 }

	esDhcp6SInterfaceGroup  OBJECT-GROUP
		OBJECTS {
		    esDhcp6ServIfPoolName,
		    esDhcp6ServIfRapidCommit,
		    esDhcp6ServIfAllowHint,
		    esDhcp6ServIfPreference,
		    esDhcp6ServIfRowStatus
		}
		STATUS current
		DESCRIPTION
			"A collection of objects providing interface-specific configuration
			for DHCPv6 Server feature."
		::= { esDhcp6ServerGroups 4 }

	esDhcp6SNonTempAddrAssignGroup  OBJECT-GROUP
		OBJECTS {
		    esDhcp6SPoolAddrPrefixAddr,
		    esDhcp6SPoolAddrPrefixLength,
		    esDhcp6SPoolAddrPrefixVLtime,
		    esDhcp6SPoolAddrPrefixPLtime,
		    esDhcp6SPoolAddrPrefixRowStatus,
		    esDhcp6SPoolAddrAssignAddr,
		    esDhcp6SPoolAddrAssignLength,
		    esDhcp6SPoolAddrAssignClientDuid,
		    esDhcp6SPoolAddrAssignSetIaid,
		    esDhcp6SPoolAddrAssignIaid,
		    esDhcp6SPoolAddrAssignVLtime,
		    esDhcp6SPoolAddrAssignPLtime,
		    esDhcp6SPoolAddrAssignRowStatus
		}
		STATUS current
		DESCRIPTION
			"A collection of objects providing non-temporary addresses configuration
			for DHCPv6 Server feature."
		::= { esDhcp6ServerGroups 5 }

    esDhcp6SPrefixDelegationGroup  OBJECT-GROUP
		OBJECTS {
		    esDhcp6SPoolPdPrefix,
		    esDhcp6SPoolPdPrefixLength,
		    esDhcp6SPoolPdClientDuid,
		    esDhcp6SPoolPdSetIaid,
		    esDhcp6SPoolPdIaid,
		    esDhcp6SPoolPdVLtime,
		    esDhcp6SPoolPdPLtime,
		    esDhcp6SPoolPdRowStatus,
		    esDhcp6SPoolPdLocPoolName,
		    esDhcp6SPoolPdLocPoolVLtime,
		    esDhcp6SPoolPdLocPoolPLtime,
		    esDhcp6SPoolPdLocPoolRowStatus
		}
		STATUS current
		DESCRIPTION
			"A collection of objects providing prefix-delegation configuration
			for DHCPv6 Server feature."
		::= { esDhcp6ServerGroups 6 }

    esDhcp6SInfoGroup  OBJECT-GROUP
		OBJECTS {
		    esDhcp6SLocalPoolFreeAddrNum,
		    esDhcp6SLocalPoolInUseAddrNum,
		    esDhcp6SBindClientLinkLocalAddr,
		    esDhcp6SBindIaT1,
		    esDhcp6SBindIaT2,
		    esDhcp6SBindVLtime,
		    esDhcp6SBindPLtime,
		    esDhcp6SBindExpire,
		    esDhcp6SBindClear
		}
		STATUS current
		DESCRIPTION
			"A collection of objects providing dynamic information for DHCPv6
			Server feature."
		::= { esDhcp6ServerGroups 7 }

END
