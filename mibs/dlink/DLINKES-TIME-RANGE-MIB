--  *****************************************************************
--  DLINKES-TIME-RANGE-MIB.mib : DLINK Time Range MIB
-- 
--  Copyright (c) 2013 D-Link Corporation, all rights reserved.
--   
--  *****************************************************************
DLINKES-TIME-RANGE-MIB DEFINITIONS ::= BEGIN

    IMPORTS
        MODULE-IDENTITY, OBJECT-TYPE, Unsigned32     
            FROM SNMPv2-SMI        
        RowStatus, DisplayString
            FROM SNMPv2-TC
        MODULE-COMPLIANCE, OBJECT-GROUP
		    FROM SNMPv2-CONF
        dlinkCommon            
            FROM DLINK-ID-REC-MIB;

     dlinkEsTimeRangeMIB MODULE-IDENTITY
         LAST-UPDATED "201708170000Z"
         ORGANIZATION "D-Link Corp."
         CONTACT-INFO
            "        D-Link Corporation

             Postal: No. 289, Sinhu 3rd Rd., Neihu District,
                     Taipei City 114, Taiwan, R.O.C
             Tel:     +886-2-66000123
             E-mail: tsd@dlink.com.tw
            "
        DESCRIPTION
            "This MIB defines time range profiles to activate features."
         
        REVISION "201708170000Z"
        DESCRIPTION
            "This is the first version of the MIB file."
         ::= { dlinkCommon 50 }


-- -----------------------------------------------------------------------------
    esTimeRangeMIBNotifications   OBJECT IDENTIFIER ::= { dlinkEsTimeRangeMIB 0 }
    esTimeRangeMIBObjects         OBJECT IDENTIFIER ::= { dlinkEsTimeRangeMIB 1 }
    esTimeRangeMIBConformance     OBJECT IDENTIFIER ::= { dlinkEsTimeRangeMIB 2 }

-- -----------------------------------------------------------------------------  
    esTimeRangeProfileTable OBJECT-TYPE
        SYNTAX          SEQUENCE OF EsTimeRangeProfileEntry
        MAX-ACCESS      not-accessible
        STATUS          current
        DESCRIPTION
             "A table consists of a list of time range profiles."
        ::= { esTimeRangeMIBObjects 1 }

    esTimeRangeProfileEntry OBJECT-TYPE
        SYNTAX          EsTimeRangeProfileEntry
        MAX-ACCESS      not-accessible
        STATUS          current
        DESCRIPTION
            "An entry contains information of a time range profile."
        INDEX { 
            esTimeRangeProfileName,
            esTimeRangeProfilePeriodType,             
            esTimeRangeProfileStartDayOfWeek,
            esTimeRangeProfileStartHour,
            esTimeRangeProfileStartMinute,
            esTimeRangeProfileEndDayOfWeek,
            esTimeRangeProfileEndHour,
            esTimeRangeProfileEndMinute      
        }
        ::= { esTimeRangeProfileTable 1 }

    EsTimeRangeProfileEntry ::=           SEQUENCE {
        esTimeRangeProfileName               DisplayString,      
	    esTimeRangeProfilePeriodType 	    INTEGER,
        esTimeRangeProfileStartDayOfWeek     INTEGER,
        esTimeRangeProfileStartHour          Unsigned32,
        esTimeRangeProfileStartMinute        Unsigned32,
        esTimeRangeProfileEndDayOfWeek       INTEGER,
        esTimeRangeProfileEndHour            Unsigned32,
        esTimeRangeProfileEndMinute          Unsigned32,      
        esTimeRangeProfileRowStatus          RowStatus
    }

    esTimeRangeProfileName           OBJECT-TYPE
        SYNTAX          DisplayString (SIZE (1..32))
        MAX-ACCESS      not-accessible
        STATUS          current
        DESCRIPTION
            "The time range name of the entry."
        ::= { esTimeRangeProfileEntry 1 }         
           
	esTimeRangeProfilePeriodType OBJECT-TYPE
		SYNTAX	INTEGER {
			daily(1),
			weekly(2)
		}
		MAX-ACCESS	    not-accessible
		STATUS	        current
	    DESCRIPTION
			"This object indicates the type of this entry.
            'daily' - Using the time of day to specify the time range.
            'weekly' - Using the day of the week and time of day to specify 
                      the time range.
            "
		::= { esTimeRangeProfileEntry 2 }

    esTimeRangeProfileStartDayOfWeek          OBJECT-TYPE
        SYNTAX          INTEGER  {
            sunday(1),
            monday(2),
            tuesday(3),
            wednesday(4),
            thursday(5),
            friday(6),
            saturday(7),
            notApplicable(8)
        }       
        MAX-ACCESS      not-accessible
        STATUS          current
        DESCRIPTION
            "This object indicates the start day of week of the entry.
            This object is meaningful when esTimeRangeProfilePeriodType is 'weekly'.
            If esTimeRangeProfilePeriodType is not 'weekly', this object is set
            to 'notApplicable'.        
            "
        ::= { esTimeRangeProfileEntry 3 }
       
    esTimeRangeProfileStartHour OBJECT-TYPE
        SYNTAX          Unsigned32 (0..23)
        MAX-ACCESS      not-accessible
        STATUS          current
        DESCRIPTION
            "This object specifies the hours component of time (24 hour format)
            at which the daily/weekly periodic start time for this entry.
            "
        ::= { esTimeRangeProfileEntry 4 }

    esTimeRangeProfileStartMinute OBJECT-TYPE
        SYNTAX          Unsigned32 (0..59)
        MAX-ACCESS      not-accessible
        STATUS          current
        DESCRIPTION
           "This object specifies the minutes component of time at which
           the daily/weekly periodic start time for this entry.
           "
        ::= { esTimeRangeProfileEntry 5 }
 
   esTimeRangeProfileEndDayOfWeek          OBJECT-TYPE
        SYNTAX          INTEGER  {
            sunday(1),
            monday(2),
            tuesday(3),
            wednesday(4),
            thursday(5),
            friday(6),
            saturday(7),
            notApplicable(8)
        }       
        MAX-ACCESS      not-accessible
        STATUS          current
        DESCRIPTION
            "This object indicates the end day of week of the entry.
            This object is meaningful when esTimeRangeProfilePeriodType is 'weekly'.
            If esTimeRangeProfilePeriodType is not 'weekly', this object is set
            to 'notApplicable'.
            "
        ::= { esTimeRangeProfileEntry 6 }
       
    esTimeRangeProfileEndHour OBJECT-TYPE
        SYNTAX          Unsigned32 (0..23)
        MAX-ACCESS      not-accessible
        STATUS          current
        DESCRIPTION
            "This object specifies the hours component of time (24 hour format)
            at which the daily/weekly periodic start time for this entry.
            "
        ::= { esTimeRangeProfileEntry 7 }

    esTimeRangeProfileEndMinute OBJECT-TYPE
        SYNTAX          Unsigned32 (0..59)
        MAX-ACCESS      not-accessible
        STATUS          current
        DESCRIPTION
            "This object specifies the minutes component of time at which
            the daily/weekly periodic end time for this entry.
            "
        ::= { esTimeRangeProfileEntry 8 }

    esTimeRangeProfileRowStatus OBJECT-TYPE
        SYNTAX          RowStatus
        MAX-ACCESS      read-create
        STATUS          current
        DESCRIPTION
            "This object indicates the RowStatus of this entry."
        ::= { esTimeRangeProfileEntry  9 }

--  ***************************************************************************	
--  Conformance
--  ***************************************************************************			   		
	esTimeRangeCompliances OBJECT IDENTIFIER ::= { esTimeRangeMIBConformance 1 }
		
	esTimeRangeCompliance MODULE-COMPLIANCE
		STATUS current
		DESCRIPTION 
			"The compliance statement for entities which implement the 
			DLINKES-TIME-RANGE-MIB."
		MODULE -- this module
		MANDATORY-GROUPS { 
            esTimeRangeProfileCfgGroup         
        }	
		
		::= { esTimeRangeCompliances 1 }
		
	esTimeRangeGroups OBJECT IDENTIFIER ::= { esTimeRangeMIBConformance 2 }
	
	esTimeRangeProfileCfgGroup OBJECT-GROUP
		OBJECTS { 
			esTimeRangeProfileRowStatus 
		}
		STATUS current
		DESCRIPTION 
			"A collection of objects providing configuration for time range profiles."
		::= { esTimeRangeGroups 1 }
	   
          
END
