-- *****************************************************************
-- DLINKES-LACP-EXT-MIB.mib : D-Link Link Aggregation Control Extenstions MIB
--
-- Copyright (c) 2013 D-Link Corporation, all rights reserved.
--
-- *****************************************************************

DLINKES-LACP-EXT-MIB DEFINITIONS ::= BEGIN

    IMPORTS
        MODULE-IDENTITY , OBJECT-TYPE, Integer32
            FROM SNMPv2-SMI
           RowStatus
               FROM SNMPv2-TC
        MODULE-COMPLIANCE, OBJECT-GROUP
            FROM SNMPv2-CONF
           InterfaceIndex
            FROM IF-MIB
           PortList
            FROM Q-BRIDGE-MIB
        dlinkCommon
            FROM DLINK-ID-REC-MIB;

    dlinkEsLacpExtMIB MODULE-IDENTITY
        LAST-UPDATED "201408180000Z"
        ORGANIZATION "D-Link Corp."
        CONTACT-INFO
            "        D-Link Corporation
             Postal: No. 289, Sinhu 3rd Rd., Neihu District,
             Taipei City 114, Taiwan, R.O.C
             Tel:     +886-2-66000123
             E-mail: tsd@dlink.com.tw
            "
        DESCRIPTION
            "The MIB module for managing D-Link LACP extensions which are
            not covered by standard MIBs."

        REVISION    "201408180000Z"
        DESCRIPTION
            "Add value srcL4Port(7), dstL4Port(8), srcDstL4Port(9)
                 on esLacpExtLoadBalanceAlgorithm for support L4 load balance algorithm."

        REVISION    "201301180000Z"
        DESCRIPTION
            "Initial revision of this MIB module."
    ::= { dlinkCommon 4 }

    esLacpExtMIBNotifications       OBJECT IDENTIFIER ::= { dlinkEsLacpExtMIB 0 }
    esLacpExtMIBObjects            OBJECT IDENTIFIER ::= { dlinkEsLacpExtMIB 1 }
    esLacpExtMIBConformance         OBJECT IDENTIFIER ::= { dlinkEsLacpExtMIB 2 }


-----------------------------------------------
--    Lacp Objects
-----------------------------------------------
    esLacpExtLoadBalanceAlgorithm OBJECT-TYPE
        SYNTAX  INTEGER {
                dstIp(1),
                dstMac(2),
                srcDstIp(3),
                srcDstMac(4),
                srcIp(5),
                srcMac(6),
                srcL4Port(7),
                dstL4Port(8),
                srcDstL4Port(9)
            }
        MAX-ACCESS  read-write
        STATUS  current
        DESCRIPTION
            "This object configures load balance algorithm that the switch uses
            to distribute packets across ports in the same channel.
            dstIp(1)  -    Specify that the switch should examine the destination
                        IP address.
            dstMac(2) -    Specify that the switch should examine the destination
                        MAC address.
            srcDstIp(3) - Specify that the switch should examine the source
                       and destination IP address.
            srcDstMac(4) - Specify that the switch should examine the source and
                       destination MAC address.
            srcIp(5) - Specify that the switch should examine the source IP
                       address.
            srcMac(6) -    Specify that the switch should examine the source MAC
                       address.
            srcL4Port(7) - Specify that the switch should examine the L4 source
                       port number.
            dstL4Port(8) - Specify that the switch should examine the L4 destination
                       port number.
            srcDstL4Port(9) - Specify that the switch should examine the L4 source
                       and destination port number.
            "
        ::= { esLacpExtMIBObjects 1 }

    esLacpExtGroupTable OBJECT-TYPE
        SYNTAX          SEQUENCE OF EsLacpExtGroupEntry
        MAX-ACCESS      not-accessible
        STATUS          current
        DESCRIPTION
            "This table consists of a list of channel group information."
        ::= { esLacpExtMIBObjects 2 }

    esLacpExtGroupEntry OBJECT-TYPE
        SYNTAX          EsLacpExtGroupEntry
        MAX-ACCESS      not-accessible
        STATUS          current
        DESCRIPTION
            "An entry presents a channel group information, which is not
            covered by standard MIB(s)."
        INDEX  { esLacpExtGroupChannelNo }
        ::= { esLacpExtGroupTable 1 }

    EsLacpExtGroupEntry ::=
        SEQUENCE {
            esLacpExtGroupChannelNo          Integer32,
            esLacpExtGroupIfIndex            InterfaceIndex,
            esLacpExtGroupType               INTEGER,
            esLacpExtGroupMemberPorts        PortList,
            esLacpExtGroupActiveMemberPorts  PortList,
            esLacpExtGroupRowStatus          RowStatus
        }

    esLacpExtGroupChannelNo OBJECT-TYPE
        SYNTAX          Integer32 (1 .. 255)
        MAX-ACCESS      not-accessible
        STATUS          current
        DESCRIPTION
            "This object indicates the channel group ID. "
        ::= { esLacpExtGroupEntry 1 }

    esLacpExtGroupIfIndex OBJECT-TYPE
        SYNTAX          InterfaceIndex
        MAX-ACCESS      read-only
        STATUS          current
        DESCRIPTION
            "The ifIndex of the channel group."
        ::= { esLacpExtGroupEntry 2 }

    esLacpExtGroupType OBJECT-TYPE
        SYNTAX  INTEGER {
            static(1),
            lacp(2)
        }
           MAX-ACCESS  read-create
        STATUS  current
        DESCRIPTION
            "This object indicates the type of channel group.
            "
        ::= { esLacpExtGroupEntry 3 }

    esLacpExtGroupMemberPorts OBJECT-TYPE
        SYNTAX          PortList
        MAX-ACCESS      read-create
        STATUS          current
        DESCRIPTION
            "This object indicates the ports which are grouped into this
            channel group.
            "
        ::= { esLacpExtGroupEntry 4 }

    esLacpExtGroupActiveMemberPorts OBJECT-TYPE
        SYNTAX          PortList
        MAX-ACCESS      read-only
        STATUS          current
        DESCRIPTION
            "This object indicates the operational bundled ports in this
            channel group.
            "
        ::= { esLacpExtGroupEntry 5 }

    esLacpExtGroupRowStatus OBJECT-TYPE
        SYNTAX          RowStatus
        MAX-ACCESS      read-create
        STATUS          current
        DESCRIPTION
            "This object indicates the status of this entry."
        ::= { esLacpExtGroupEntry 6 }

-----------------------------------------------
--    Lacp Conformance
-----------------------------------------------
    esLacpExtCompliances       OBJECT IDENTIFIER ::= { esLacpExtMIBConformance 1 }


    esLacpExtCompliance MODULE-COMPLIANCE
        STATUS current
        DESCRIPTION
            "The compliance statement for entities which implement the
            DLINKES-LACP-EXT-MIB."
        MODULE
        MANDATORY-GROUPS {
            esLacpExtAlgGroup,
            esLacpExtChannelGrpInfoGroup
        }
        ::= { esLacpExtCompliances 1 }

    esLacpExtGroups           OBJECT IDENTIFIER ::= { esLacpExtMIBConformance 2 }

    esLacpExtAlgGroup OBJECT-GROUP
          OBJECTS {
             esLacpExtLoadBalanceAlgorithm
            }
        STATUS          current
        DESCRIPTION
            "A collection of objects providing information about the algorithm of
            link aggregation load sharing."
        ::= { esLacpExtGroups 1 }

    esLacpExtChannelGrpInfoGroup OBJECT-GROUP
          OBJECTS {
              esLacpExtGroupIfIndex,
            esLacpExtGroupType,
            esLacpExtGroupMemberPorts,
            esLacpExtGroupActiveMemberPorts,
            esLacpExtGroupRowStatus
        }
        STATUS current
        DESCRIPTION
            "A collection of objects providing configuration of channel groups."
        ::= { esLacpExtGroups 2 }


END
