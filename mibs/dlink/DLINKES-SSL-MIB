--  *****************************************************************
--  DLINKES-SSL-MIB.mib : Secure Socket Layer MIB
--
--  Copyright (c) 2016 D-Link Corporation, all rights reserved.
--
--  *****************************************************************
DLINKES-SSL-MIB DEFINITIONS ::= BEGIN

    IMPORTS
        MODULE-IDENTITY,
        OBJECT-TYPE,
        Integer32,
        Unsigned32
            FROM SNMPv2-SMI
        RowStatus, TruthValue,DisplayString
            FROM SNMPv2-TC
        OBJECT-GROUP, MODULE-COMPLIANCE
            FROM SNMPv2-CONF
        InetAddressType,InetAddress
            FROM INET-ADDRESS-MIB
        dlinkCommon
            FROM DLINK-ID-REC-MIB;


    dlinkEsSslMIB MODULE-IDENTITY
        LAST-UPDATED "201512240000Z"
        ORGANIZATION "D-Link Corp."
        CONTACT-INFO
            "        D-Link Corporation

             Postal: No. 289, Sinhu 3rd Rd., Neihu District,
                     Taipei City 114, Taiwan, R.O.C
             Tel:     +886-2-66000123
             E-mail: tsd@dlink.com.tw
            "
        DESCRIPTION
            "This MIB module defines objects for Secure Socket Layer (SSL)."
        REVISION "201512240000Z"
        DESCRIPTION
            "This is the first version of the MIB file for 'SSL'
             functionality."
    ::= { dlinkCommon 7}

-- -----------------------------------------------------------------------------
    dlinkSslNotifications    OBJECT IDENTIFIER ::= { dlinkEsSslMIB 0 }
    dlinkSslObjects          OBJECT IDENTIFIER ::= { dlinkEsSslMIB 1 }
    dlinkSslConformance      OBJECT IDENTIFIER ::= { dlinkEsSslMIB 2 }

-- -----------------------------------------------------------------------------
    esSslCryptoPkiImportCertTable OBJECT-TYPE
        SYNTAX          SEQUENCE OF EsSslCryptoPkiImportCertEntry
        MAX-ACCESS      not-accessible
        STATUS          current
        DESCRIPTION
            "A table of importing certificates and key pairs. There will at any
            time be either 0 or 1 rows in this table, and the only valid index
            for this table is 1.  It is only a table so that we may take
            advantage of the RowStatus textual convention for configuring the
            importing parameters.
            The row in this table is volatile; that is, it is lost if the SNMP
            agent is rebooted."
           ::= { dlinkSslObjects 1 }

    esSslCryptoPkiImportCertEntry OBJECT-TYPE
        SYNTAX          EsSslCryptoPkiImportCertEntry
        MAX-ACCESS      not-accessible
        STATUS          current
        DESCRIPTION
            "The row in the esSslCryptoPkiImportCertTable containing the importing
            parameters.
            Once an entry has been activated, the importing parameters cannot be
            modified.  In order to use a new value, you need delete the old entry
            and create a new one."
        INDEX    { esSslCryPkiImportCertIndex }
        ::= { esSslCryptoPkiImportCertTable 1 }

    EsSslCryptoPkiImportCertEntry ::=
        SEQUENCE {
            esSslCryPkiImportCertIndex           Integer32,
            esSslCryPkiImportCertTrustPoint      DisplayString,
            esSslCryPkiImportCertSrcType         INTEGER,
            esSslCryPkiImportFilename            DisplayString,
            esSslCryPkiImportCertAddrType        InetAddressType,
            esSslCryPkiImportCertAddr            InetAddress,
            esSslCryPkiImportFileType            BITS,
            esSslCryPkiImportPwdPhrase           DisplayString,
            esSslCryPkiImportErrorStatus         DisplayString,
            esSslCryPkiImportRowStatus           RowStatus
        }

    esSslCryPkiImportCertIndex OBJECT-TYPE
        SYNTAX          Integer32 (1)
        MAX-ACCESS      not-accessible
        STATUS          current
        DESCRIPTION
            "The index which uniquely identifies this row."
        ::= { esSslCryptoPkiImportCertEntry 1 }

    esSslCryPkiImportCertTrustPoint OBJECT-TYPE
        SYNTAX          DisplayString  (SIZE (0..32))
        MAX-ACCESS      read-create
        STATUS          current
        DESCRIPTION
            "Name of the trustpoint to which the certificates and key pairs
             will be imported."
        DEFVAL      { "" }
        ::= {  esSslCryptoPkiImportCertEntry 2 }

    esSslCryPkiImportCertSrcType OBJECT-TYPE
        SYNTAX          INTEGER {
            filesystem(1),
            tftp(2) }
        MAX-ACCESS      read-create
        STATUS          current
        DESCRIPTION
            "An indication of the source from where the certificates/key pairs
             will be imported.
             filesystem(1) - The certificates/key pairs will be imported from the
                switch's file system.
             tftp(2) - The certificates/key pairs will be imported via tftp."
        DEFVAL   { filesystem }
        ::= { esSslCryptoPkiImportCertEntry 3 }

    esSslCryPkiImportFilename OBJECT-TYPE
        SYNTAX          DisplayString  (SIZE (0..64))
        MAX-ACCESS      read-create
        STATUS          current
        DESCRIPTION
            "If esSslCryPkiImportCertSrcType is 'filesystem', this object
            indicates the file name and path of the importing certificate
            and key pairs in switch's file system. The supported file systems
            are project dependent.
            If esSslCryPkiImportCertSrcType is 'tftp', this object indicates
            the file name and path where the switch should import via TFTP
            server. By default, the switch will appends this name with .ca,
            .prv and .crt for CA certificate, private key and certificate
            respectively."
        ::= {  esSslCryptoPkiImportCertEntry 4 }

    esSslCryPkiImportCertAddrType OBJECT-TYPE
        SYNTAX          InetAddressType
        MAX-ACCESS      read-create
        STATUS          current
        DESCRIPTION
            "The type of address in the corresponding esSslCryPkiImportCertAddr
            object. "
           ::= { esSslCryptoPkiImportCertEntry 5 }

    esSslCryPkiImportCertAddr OBJECT-TYPE
        SYNTAX          InetAddress
        MAX-ACCESS      read-create
        STATUS          current
        DESCRIPTION
            "The address of TFTP server."
        ::= {  esSslCryptoPkiImportCertEntry 6 }

    esSslCryPkiImportPwdPhrase OBJECT-TYPE
        SYNTAX          DisplayString  (SIZE (0..64))
        MAX-ACCESS      read-create
        STATUS          current
        DESCRIPTION
            "Specifies the encrypted password phrase that is used to undo
            encryption when the private keys are imported."
        ::= {  esSslCryptoPkiImportCertEntry 7 }

    esSslCryPkiImportFileType OBJECT-TYPE
        SYNTAX BITS {
            ca(0),
            local(1)}
        MAX-ACCESS      read-create
        STATUS          current
        DESCRIPTION
            "An object indicates what kind of certificate will be imported.
            Setting a type's bit to 1 means the type of certificate will
            be imported.
            ca (0)    - Import CA certificate.
            local (1) - Import local certificate and key pairs."
--        DEFVAL { {} }   no bits set.
        ::= { esSslCryptoPkiImportCertEntry 8 }

    esSslCryPkiImportErrorStatus OBJECT-TYPE
        SYNTAX          DisplayString (SIZE (0..255))
        MAX-ACCESS      read-only
        STATUS          current
        DESCRIPTION
            "A textual description of the current status of the importing.
            The status information includes: idle, in progress, success, aborted,
            idle, corruptFile, no server...."
           ::= { esSslCryptoPkiImportCertEntry 9 }

    esSslCryPkiImportRowStatus OBJECT-TYPE
        SYNTAX     RowStatus
        MAX-ACCESS read-create
        STATUS     current
        DESCRIPTION
            "The status of this import entry.  This object may not be set to
            'active' if the following columnar objects exist in this row:
            esSslCryPkiImportCertTrustPoint, esSslCryPkiImportFilename, and
            esSslCryPkiImportFileType.
            Besides, if esSslCryPkiImportCertSrcType is 'tftp' the columnar
            objects esSslCryPkiImportCertAddrType and esSslCryPkiImportCertAddr
            must be configured."
        ::= { esSslCryptoPkiImportCertEntry 10 }

-- -----------------------------------------------------------------------------
    esSslConfiguration  OBJECT IDENTIFIER ::= { dlinkSslObjects 2 }

    esSslCryptoPkiTrustpointTable  OBJECT-TYPE
        SYNTAX          SEQUENCE OF EsSslCryptoPkiTrustpointEntry
        MAX-ACCESS      not-accessible
        STATUS          current
        DESCRIPTION
            "A table defines and configures trustpoint(s) in the switch."
        ::= { esSslConfiguration 1 }

    esSslCryptoPkiTrustpointEntry OBJECT-TYPE
        SYNTAX          EsSslCryptoPkiTrustpointEntry
        MAX-ACCESS      not-accessible
        STATUS          current
        DESCRIPTION
            "The row in the esSslCryptoPkiTrustpointTable containing the
            trustpoint parameters.
            An entry is created/removed when a name for a specific
            trustpoint is generated or deleted via CLI or by issuing appropriate
            sets to this table using snmp."
        INDEX  { esSslCryptoPkiTrustpointName }
        ::= { esSslCryptoPkiTrustpointTable 1 }

    EsSslCryptoPkiTrustpointEntry ::=
        SEQUENCE {
            esSslCryptoPkiTrustpointName         DisplayString,
            esSslCryptoPkiTrustpointPrimary      TruthValue,
            esSslCryptoPkiTrustpointRowStatus    RowStatus }

    esSslCryptoPkiTrustpointName OBJECT-TYPE
        SYNTAX          DisplayString  (SIZE (1..32))
        MAX-ACCESS      not-accessible
        STATUS          current
        DESCRIPTION
            "Name of the trustpoint for which this entry pertains to."
        ::= { esSslCryptoPkiTrustpointEntry 1 }

    esSslCryptoPkiTrustpointPrimary OBJECT-TYPE
        SYNTAX          TruthValue
        MAX-ACCESS      read-create
        STATUS          current
        DESCRIPTION
            "This object specifies a given trustpoint as primary.
            This trustpoint can be used as default trustpoint when
            the application doesn't explicitly specify which certificate
            authority (CA) trustpoint should be used.

            Only one trustpoint can be specified as primary. That is the
            last trustpoint you specify as primary will overwrite the
            previous one."
        DEFVAL    { false }
        ::= { esSslCryptoPkiTrustpointEntry 2 }

    esSslCryptoPkiTrustpointRowStatus OBJECT-TYPE
        SYNTAX          RowStatus
        MAX-ACCESS      read-create
        STATUS          current
        DESCRIPTION
            "Status of this trustpoint."
        ::= { esSslCryptoPkiTrustpointEntry 3 }

-- -----------------------------------------------------------------------------
    esSslCryptoPkiCertTable  OBJECT-TYPE
        SYNTAX          SEQUENCE OF EsSslCryptoPkiCertEntry
        MAX-ACCESS      not-accessible
        STATUS          current
        DESCRIPTION
            "A table manages CA certificate(s) or the switch
            certificate(s) and keys."
        ::= { esSslConfiguration 2 }

    esSslCryptoPkiCertEntry OBJECT-TYPE
        SYNTAX          EsSslCryptoPkiCertEntry
        MAX-ACCESS      not-accessible
        STATUS          current
        DESCRIPTION
            "The row in the esSslCryptoPkiCertTable containing the
            parameters of a certificate.
            An entry in this table appears automatically whenever
            the certificate or keypairs is imported successfully.
            An entry is removed when a certificate name is deleted
            via CLI or by issuing appropriate sets to this table using snmp."
        INDEX  { esSslCryptoPkiTrustpointName,esSslCryptoPkiCertName }
        ::= { esSslCryptoPkiCertTable 1 }

    EsSslCryptoPkiCertEntry ::=
        SEQUENCE {
            esSslCryptoPkiCertName           DisplayString,
            esSslCryptoPkiCertCAType         INTEGER,
            esSslCryptoPkiCertRemoveCtrl     INTEGER }

    esSslCryptoPkiCertName OBJECT-TYPE
        SYNTAX          DisplayString  (SIZE (0..32))
        MAX-ACCESS      not-accessible
        STATUS          current
        DESCRIPTION
            "Indicates the name of the certificate for which this entry
            pertains to."
        ::= { esSslCryptoPkiCertEntry 1 }

    esSslCryptoPkiCertCAType OBJECT-TYPE
        SYNTAX  INTEGER {
            ca(1),
            localCertificate(2),
            localPrivateKey(3) }
        MAX-ACCESS      read-only
        STATUS          current
        DESCRIPTION
            "This object specifies the type of the certificate.
            ca(1) -  CA certificate.
            localCertificate(2) - local certificate.
            localPrivateKey(3) -  local private key."
        ::= { esSslCryptoPkiCertEntry 2 }

    esSslCryptoPkiCertRemoveCtrl OBJECT-TYPE
        SYNTAX          INTEGER {
            delete(1),
            noOp(2) }
        MAX-ACCESS      read-write
        STATUS          current
        DESCRIPTION
            "This object is used to delete this entry.
            No action is taken if this object is set to 'noOp'.
            When read, the value 'noOp' is returned."
        ::= { esSslCryptoPkiCertEntry 3 }

-- -----------------------------------------------------------------------------
   esSslServicePolicyTable  OBJECT-TYPE
        SYNTAX          SEQUENCE OF EsSslServicePolicyEntry
        MAX-ACCESS      not-accessible
        STATUS          current
        DESCRIPTION
            "A table controlls the parameters of SSL service policies."
        ::= { esSslConfiguration 3 }

    esSslServicePolicyEntry OBJECT-TYPE
        SYNTAX          EsSslServicePolicyEntry
        MAX-ACCESS      not-accessible
        STATUS          current
        DESCRIPTION
            "The row in the esSslServicePolicyTable containing the
            parameters of a SSL service policy.

            An entry is created/removed when a name for a specific
            policy is generated or deleted via CLI or by issuing appropriate
            sets to this table using snmp."
        INDEX  { esSslServicePolicyName }
        ::= { esSslServicePolicyTable 1 }

    EsSslServicePolicyEntry ::=
        SEQUENCE {
            esSslServicePolicyName               DisplayString,
            esSslServicePolicyCipherSuites       BITS,
            esSslServicePolicyTrustpoint         DisplayString,
            esSslServicePolicyCacheTimeout       Unsigned32,
            esSslServicePolicyRowStatus          RowStatus }

    esSslServicePolicyName OBJECT-TYPE
        SYNTAX          DisplayString  (SIZE (1..32))
        MAX-ACCESS      not-accessible
        STATUS          current
        DESCRIPTION
            "Indicates the name of the policy for which this entry pertains to."
        ::= { esSslServicePolicyEntry 1 }

    esSslServicePolicyCipherSuites OBJECT-TYPE
        SYNTAX          BITS {
            dheDss3DesEdeCbcSha(0),
            rsa3desEdeCbcSha(1),
            rsaRc4128Sha(2),
            rsaRc4128Md5(3),
            rsaExportRc440Md5(4) }
        MAX-ACCESS      read-create
        STATUS          current
        DESCRIPTION
            "This object indicates a ciphersuite should be used by the secure
            service when negotiating a connection with a remote peer. Setting
            a ciphersuite's bit to 1 enables the ciphersuite. Setting this bit
            to 0 disables it.

            dheDss3DesEdeCbcSha(0): Uses DH key exchange with 3DES-EDE-CBC
                encryption and SHA for message digest.

            rsa3desEdeCbcSha(1): Uses RSA key exchange with 3DES-EDE-CBC for
                message encryption and SHA for message digest.

            rsaRc4128Sha(2): Uses RSA key exchange with RC4 128-bit
                encryption for message encryption and SHA for message digest.

            rsaRc4128Md5(3): Uses RSA key exchange with RC4 128-bit
                encryption for message encryption and MD5 for message digest.

            rsaExportRc440Md5(4): Uses RSA EXPORT key exchange with RC4 40
                bits for message encryption and MD5 for message digest."
--        DEFVAL  { { dheDss3DesEdeCbcSha, rsa3desEdeCbcSha, rsaRc4128Sha,
--                    rsaRc4128Md5, rsaExportRc440Md5 } }
        ::= { esSslServicePolicyEntry 2}


    esSslServicePolicyTrustpoint OBJECT-TYPE
        SYNTAX          DisplayString  (SIZE (0..32))
        MAX-ACCESS      read-create
        STATUS          current
        DESCRIPTION
            "Specifies the name of the trustpoint that should be used in SSL
            handshake.

            When secure-trustpoint is not specified, the primary trustpoint
            (the value of esSslCryptoPkiTrustpointPrimary is 'true') will be
            used.

            If no trustpoint is specified (empty string), the built-in
            certificate/key pairs will be used."
        ::= { esSslServicePolicyEntry 3 }

    esSslServicePolicyCacheTimeout OBJECT-TYPE
        SYNTAX          Unsigned32 (60..86400)
        MAX-ACCESS      read-create
        STATUS          current
        DESCRIPTION
            "This object indicates the Cache Timeout value in the policy for
            SSL module to refresh the session resume data kept in database."
        DEFVAL    { 600 }
        ::= { esSslServicePolicyEntry 4}

    esSslServicePolicyRowStatus OBJECT-TYPE
        SYNTAX          RowStatus
        MAX-ACCESS      read-create
        STATUS          current
        DESCRIPTION
               "Status of this policy."
        ::= { esSslServicePolicyEntry 5 }

-- -----------------------------------------------------------------------------
-- Conformance
-- -----------------------------------------------------------------------------
    dlinkSslCompliances OBJECT IDENTIFIER ::= { dlinkSslConformance 1 }

    dlinkSslGroups OBJECT IDENTIFIER ::= { dlinkSslConformance 2 }

    dlinkSslCompliance MODULE-COMPLIANCE
        STATUS   current
        DESCRIPTION
            "The compliance statement for entities which implement the
            DLINKES-SSL-MIB."
        MODULE MANDATORY-GROUPS {
            esSslImportCertGroup,
            esSslTrustPointConfigGroup,
            esSslServicePolicyGroup }
        ::= { dlinkSslCompliances 1 }

    esSslImportCertGroup OBJECT-GROUP
        OBJECTS {
            esSslCryPkiImportCertTrustPoint,
            esSslCryPkiImportCertSrcType,
            esSslCryPkiImportFilename,
            esSslCryPkiImportCertAddrType,
            esSslCryPkiImportCertAddr,
            esSslCryPkiImportPwdPhrase,
            esSslCryPkiImportFileType,
            esSslCryPkiImportErrorStatus,
            esSslCryPkiImportRowStatus }
        STATUS current
        DESCRIPTION
            "A collection of objects for manage importing certificates and key pairs."
        ::= { dlinkSslGroups 1 }

    esSslTrustPointConfigGroup OBJECT-GROUP
        OBJECTS {
            esSslCryptoPkiTrustpointPrimary,
            esSslCryptoPkiTrustpointRowStatus,
            esSslCryptoPkiCertCAType,
            esSslCryptoPkiCertRemoveCtrl }
        STATUS current
        DESCRIPTION
            "A collection of objects for manage trustpoints and certificates and key pairs."
        ::= { dlinkSslGroups 2 }

    esSslServicePolicyGroup OBJECT-GROUP
        OBJECTS {
            esSslServicePolicyCipherSuites,
            esSslServicePolicyTrustpoint,
            esSslServicePolicyCacheTimeout,
            esSslServicePolicyRowStatus }
        STATUS current
            DESCRIPTION
                "A collection of objects for manage trustpoints and certificates and key pairs."
            ::= { dlinkSslGroups 3 }
END
