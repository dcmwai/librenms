-- *****************************************************************
-- DLINKES-AAA-AUTH-MIB: D-Link AAA Authentication MIB
--
--  Copyright (c) 2013 D-Link Corporation, all rights reserved.
--
-- *****************************************************************

DLINKES-AAA-AUTH-MIB DEFINITIONS ::= BEGIN

    IMPORTS
        MODULE-IDENTITY,  OBJECT-TYPE
            FROM SNMPv2-SMI
        MODULE-COMPLIANCE, OBJECT-GROUP
            FROM SNMPv2-CONF
        RowStatus
            FROM SNMPv2-TC
        esAaaMIBObjects, EsAaaSessionType,
        EsAaaMethodListName, EsAaaMethodPriority,
        EsAaaMethodName
            FROM DLINKES-AAA-COMMON-MIB;


    dlinkEsAaaAuthenticationMIB MODULE-IDENTITY
        LAST-UPDATED    "201707100000Z"
        ORGANIZATION    "D-Link Corp."
        CONTACT-INFO
            "       D-Link Corporation
            Postal: No. 289, Sinhu 3rd Rd., Neihu District,
                    Taipei City 114, Taiwan, R.O.C
            Tel:    +886-2-66000123
            E-mail: tsd@dlink.com.tw
            "
        DESCRIPTION
            "This MIB module defines objects for authentication feature
            which is based on Authentication, Authorization,
            Accounting (AAA) protocols."
        REVISION        "201707100000Z"
        DESCRIPTION
            "This is the first version of the MIB. 
            "
       ::= { esAaaMIBObjects 4 }


-- ----------------------------------------------------------------------------- 
    esAaaAuthMIBNotifications 	OBJECT IDENTIFIER ::= { dlinkEsAaaAuthenticationMIB 0 }
    esAaaAuthMIBObjects	        OBJECT IDENTIFIER ::= { dlinkEsAaaAuthenticationMIB 1 }
    esAaaAuthMIBConformance	    OBJECT IDENTIFIER ::= { dlinkEsAaaAuthenticationMIB 2 }

-- -----------------------------------------------------------------------------
    esAaaAuthGenericMethodTable OBJECT-TYPE
        SYNTAX          SEQUENCE OF EsAaaAuthGenericMethodEntry
        MAX-ACCESS      not-accessible
        STATUS          current
        DESCRIPTION
            "This table contains entries for AAA authentication
            methods configured for Login/enable/dot1x/MAC authentication/web/jwac.

            The following table describes the examples.

            Type     Method List Name    Priority Method
            -----    ------------------  -------- ------------
            login    default             1        radius
            login    default             2        auth_rad
            login    default             3        tacacs+
            login    default             4        none
            login    ssh_login           1        radius
            login    ssh_login           2        none
            login    tel_login           1        tacacs+
            enable   default             1        radius
            enable   default             2        tacacs+
            dot1x    default             1        radius
            dot1x    default             2        local
            macAuth  default             1        radius
            macAuth  default             2        local
            web      default             1        radius
            web      default             2        local
            jwac     default             1        radius
            jwac     default             2        local
           "
        ::= { esAaaAuthMIBObjects 1 }

    esAaaAuthGenericMethodEntry OBJECT-TYPE
        SYNTAX          EsAaaAuthGenericMethodEntry
        MAX-ACCESS      not-accessible
        STATUS          current
        DESCRIPTION
            "An entry defines a method which is groupped into a method list. 
            "
        INDEX       {
            esAaaAuthGenMethodLstType,
            esAaaAuthGenMethodLstName,
            esAaaAuthGenMethodPriority
        }
        ::= { esAaaAuthGenericMethodTable 1 }

    EsAaaAuthGenericMethodEntry ::=
        SEQUENCE {
            esAaaAuthGenMethodLstType      INTEGER,
            esAaaAuthGenMethodLstName      EsAaaMethodListName,
            esAaaAuthGenMethodPriority     EsAaaMethodPriority,
            esAaaAuthGenMethodName         EsAaaMethodName,
            esAaaAuthGenMethodRowStatus    RowStatus
        }

    esAaaAuthGenMethodLstType OBJECT-TYPE
        SYNTAX	        INTEGER {
            enable(1),
            login(2),
            dot1x(3),
            jwac(4),
            macAuth(5),
            web(6),
            igmpAuth(7),
            mldAuth(8)
        }
        MAX-ACCESS      not-accessible
        STATUS	        current
        DESCRIPTION
            "This object indicates the type for which the method 
            list will be used.

            enable(1) - for determining the access to the privileged EXEC level.
            login(2) - for login authentication.
            dot1x(3) -  for 802.1x authentication.
            jwac(4)  - for JWAC authentication.
            macAuth(5) - for MAC authentication.
            web(6) - for Web authentication.
            igmpAuth(7) - for IGMP authentication.
            mldAuth(8) - for MLD authentication.

            Note: Not all method list types defined need to be supported.
            "
        ::= { esAaaAuthGenericMethodEntry 1 }

    esAaaAuthGenMethodLstName OBJECT-TYPE
        SYNTAX          EsAaaMethodListName
        MAX-ACCESS      not-accessible
        STATUS          current
        DESCRIPTION
            "This object indicates the name of the authentication method list.
           
            If esAaaAuthGenMethodLstType is not 'login', only 'default' 
            can be specified for esAaaAuthGenMethodLstName.
            For the type which only supports 'default' method list name, the
            configured method list will take effect without being explicitly applied. 
            If the type is 'login', the method list will take effect after
            the method list is applied in esAaaAuthLoginApplyTable.           
            "
        ::= { esAaaAuthGenericMethodEntry 2 }

    esAaaAuthGenMethodPriority OBJECT-TYPE
        SYNTAX          EsAaaMethodPriority
        MAX-ACCESS      not-accessible
        STATUS          current
        DESCRIPTION
           "This is the method priority of a method within a method list.
           "
        ::= { esAaaAuthGenericMethodEntry 3 }

    esAaaAuthGenMethodName OBJECT-TYPE
        SYNTAX          EsAaaMethodName
        MAX-ACCESS      read-create
        STATUS          current
        DESCRIPTION
            "This object indicates the authentication method name.
            "
        ::= { esAaaAuthGenericMethodEntry 4 }


    esAaaAuthGenMethodRowStatus OBJECT-TYPE
        SYNTAX      RowStatus
        MAX-ACCESS  read-create
        STATUS      current
        DESCRIPTION
            "The status of entry.

            Before modify the higher method, must destroy the lower method in method list.
            "
        ::= { esAaaAuthGenericMethodEntry 5 }

-- -----------------------------------------------------------------------------
    esAaaAuthLogin    OBJECT IDENTIFIER ::= { esAaaAuthMIBObjects 2 }
    
    esAaaAuthLoginApplyTable OBJECT-TYPE
        SYNTAX          SEQUENCE OF EsAaaAuthLoginApplyEntry
        MAX-ACCESS      not-accessible
        STATUS          current
        DESCRIPTION
            "This table contains entries for AAA authentication
            apply configured for Login.

            The following table describes the authentication commands apply.

            Session MethodListName
            ------- ------------------
            telnet  default
            console cons_auth
            ssh     ssh_login
            "
        ::= { esAaaAuthLogin 1 }

    esAaaAuthLoginApplyEntry OBJECT-TYPE
        SYNTAX          EsAaaAuthLoginApplyEntry
        MAX-ACCESS      not-accessible
        STATUS          current
        DESCRIPTION
            "An entry containing the session of an authentication
             application used for Login.
            "
        INDEX       {
            esAaaAuthLoginApplySession
        }
        ::= { esAaaAuthLoginApplyTable 1 }


    EsAaaAuthLoginApplyEntry ::=        SEQUENCE {
        esAaaAuthLoginApplySession       EsAaaSessionType,
        esAaaAuthLoginApplyListName      EsAaaMethodListName,
        esAaaAuthLoginApplyRowStatus     RowStatus
    }

    esAaaAuthLoginApplySession OBJECT-TYPE
        SYNTAX           EsAaaSessionType
        MAX-ACCESS       not-accessible
        STATUS           current
        DESCRIPTION
            "This object indicates the session type of the entry.       
            "
        ::= { esAaaAuthLoginApplyEntry 1 }

    esAaaAuthLoginApplyListName OBJECT-TYPE
        SYNTAX          EsAaaMethodListName
        MAX-ACCESS      read-create
        STATUS          current
        DESCRIPTION
            "This object indicates the method list name of the entry.           
            "
        ::= { esAaaAuthLoginApplyEntry 2 }
        
    esAaaAuthLoginApplyRowStatus OBJECT-TYPE
        SYNTAX           RowStatus
        MAX-ACCESS       read-create
        STATUS           current
        DESCRIPTION
            "The status of this entry.
            "
        ::= { esAaaAuthLoginApplyEntry 3 }



--****************************************************************************
-- Conformance
--****************************************************************************
  
    esAaaAuthMIBCompliances OBJECT IDENTIFIER ::= { esAaaAuthMIBConformance 1 }


-- compliance statements

    esAaaAuthMIBCompliance MODULE-COMPLIANCE
        STATUS      current
        DESCRIPTION
            "The compliance statement for entities which
             implement the DLINKES-AAA-AUTH-MIB."
        MODULE      -- this module
        MANDATORY-GROUPS       {
            esAaaAuthMethodListGroup,
            esAaaAuthcLoginMethodApplyGroup              
        }              
        ::= { esAaaAuthMIBCompliances 1 }

-- units of conformance

    esAaaAuthMIBGroups      OBJECT IDENTIFIER ::=  { esAaaAuthMIBConformance 2 }

    esAaaAuthMethodListGroup OBJECT-GROUP
        OBJECTS {
            esAaaAuthGenMethodName,     
            esAaaAuthGenMethodRowStatus
        }
        STATUS      current
        DESCRIPTION
            "A collection of objects provides the method list for  AAA
            authentication.
            "
        ::= { esAaaAuthMIBGroups 1 }


    esAaaAuthcLoginMethodApplyGroup OBJECT-GROUP
        OBJECTS {
            esAaaAuthLoginApplyListName,
            esAaaAuthLoginApplyRowStatus
        }
        STATUS  current
        DESCRIPTION
            "A collection of objects provides configuration to apply
            AAA method list for login authentication.
            "
        ::= { esAaaAuthMIBGroups 2 }

END
