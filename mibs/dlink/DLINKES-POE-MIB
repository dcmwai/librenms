-- *****************************************************************
-- DLINKES-POE-MIB.mib : D-Link extensions to POWER-ETHERNET-MIB (PoE)
--
-- Copyright (c) 2013 D-Link Corporation, all rights reserved.
--
-- *****************************************************************
DLINKES-POE-MIB DEFINITIONS ::= BEGIN

IMPORTS
    OBJECT-GROUP, MODULE-COMPLIANCE, NOTIFICATION-GROUP
                    FROM SNMPv2-CONF
    MODULE-IDENTITY, OBJECT-TYPE, NOTIFICATION-TYPE, Integer32,
    Unsigned32
                    FROM SNMPv2-SMI
    DisplayString,TruthValue
                    FROM SNMPv2-TC
    InetAddressType, InetAddress
                    FROM INET-ADDRESS-MIB
    PortList, VlanId
                    FROM Q-BRIDGE-MIB
    pethMainPseGroupIndex, pethPsePortIndex, pethPsePortShortCounter,
    pethPsePortOverLoadCounter, pethPsePortPowerDeniedCounter
                    FROM POWER-ETHERNET-MIB
    dlinkCommon
                    FROM DLINK-ID-REC-MIB;


    dlinkEsPoeExtMIB MODULE-IDENTITY
        LAST-UPDATED "202104200000Z"
        ORGANIZATION "D-Link Corp."
        CONTACT-INFO
                "        D-Link Corporation
                 Postal: No. 289, Sinhu 3rd Rd., Neihu District,
                         Taipei City 114, Taiwan, R.O.C
                 Tel:     +886-2-66000123
                 E-mail: tsd@dlink.com.tw
                "
        DESCRIPTION
                "A MIB module for extending POWER-ETHERNET-MIB specified in
                RFC 3621.
                "
        REVISION "202104200000Z"
        DESCRIPTION
                 "Add PoE Guard Band."
        REVISION "202104160000Z"
        DESCRIPTION
                 "Add dPoeGroupPerpetual object."
        REVISION "201810090000Z"
        DESCRIPTION
                 "Add pd alive tables to support PD alive check feature."
        REVISION "201305290000Z"
        DESCRIPTION
                 "Initial version of this MIB module."
        ::= { dlinkCommon 24 }

-- -----------------------------------------------------------------------------
    esPoeMIBNotifications   OBJECT IDENTIFIER ::= { dlinkEsPoeExtMIB 0 }
    esPoeMIBObjects         OBJECT IDENTIFIER ::= { dlinkEsPoeExtMIB 1 }
    esPoeMIBConformance     OBJECT IDENTIFIER ::= { dlinkEsPoeExtMIB 2 }

--------------------------------------------------------------------------------
    esPoeGroupCfgTable OBJECT-TYPE
        SYNTAX          SEQUENCE OF EsPoeGroupCfgEntry
        MAX-ACCESS      not-accessible
        STATUS          current
        DESCRIPTION
            "This table consists of a list of group configurations for PoE.
            Group means box in the stack or module in a rack.
            For non-modular devices, the pethMainPseGroupIndex is 1.
            "
        ::= { esPoeMIBObjects 1 }

    esPoeGroupCfgEntry OBJECT-TYPE
        SYNTAX          EsPoeGroupCfgEntry
        MAX-ACCESS      not-accessible
        STATUS          current
        DESCRIPTION
            "An entry contains the system configuration of the PoE on a group."
        INDEX { pethMainPseGroupIndex }
        ::= { esPoeGroupCfgTable 1 }

    EsPoeGroupCfgEntry ::= SEQUENCE {
             esPoeGroupPolicyPreempt        TruthValue,
             esPoeGroupClearIfStatistic     PortList,
             esPoeGroupGuardBand            Unsigned32,
             esPoeGroupPerpetual            TruthValue
        }

    esPoeGroupPolicyPreempt OBJECT-TYPE
        SYNTAX          TruthValue
        MAX-ACCESS      read-write
        STATUS          current
        DESCRIPTION
            "This object configures whether to disconnect the PD which is powered
            with lower priority in order to release the power to the new connected
            PD with higher priority under power shortage condition.
            If this object is 'false', then the policy is first in first serviced.
            Thus the new PD will not be serviced if the power budget is running out.
            If this object is 'true', then the power provisioned to PD
            with lower priority can be preempted to release the power to the new
            connected PD with higher priority. "
        DEFVAL { false }
        ::= { esPoeGroupCfgEntry 1 }

    esPoeGroupClearIfStatistic OBJECT-TYPE
        SYNTAX          PortList
        MAX-ACCESS      read-write
        STATUS          current
        DESCRIPTION
            "This object is used to clear the PoE statistics of pethPsePortEntry
             for specified ports.
            "
        ::= { esPoeGroupCfgEntry 2 }

    esPoeGroupGuardBand OBJECT-TYPE
        SYNTAX Unsigned32
        UNITS
            "milliwatts"
        MAX-ACCESS read-write
        STATUS current
        DESCRIPTION
            "Configures the amount of power to be preserved for guard band protection.
            The PoE guard-band can provide protection PoE enabled ports from being
            powered off and then ON when there is a sudden spike in the consumed power
            of PDs. The specified amount of guard band power is preserved to provide
            the regulation during sudden spike in the consumed power of PDs."
        ::= { esPoeGroupCfgEntry 3 }

    esPoeGroupPerpetual OBJECT-TYPE
        SYNTAX          TruthValue
        MAX-ACCESS      read-write
        STATUS          current
        DESCRIPTION
            "This object configures poe perpetual state. If the unit does not support
            poe perpetual, then this object cannot be set to 'true'. "
        DEFVAL { false }
        ::= { esPoeGroupCfgEntry 4 }

-------------------------------------------------------------------------------
    esPoeGroupInfoTable OBJECT-TYPE
        SYNTAX        SEQUENCE OF EsPoeGroupInfoEntry
        MAX-ACCESS    not-accessible
        STATUS        current
        DESCRIPTION
             "This table consists of a list of PoE information for groups."
        ::= { esPoeMIBObjects 2 }

    esPoeGroupInfoEntry OBJECT-TYPE
        SYNTAX        EsPoeGroupInfoEntry
        MAX-ACCESS    not-accessible
        STATUS        current
        DESCRIPTION
             "An entry contains the system information of the PoE on a group."
        INDEX { pethMainPseGroupIndex }
        ::= { esPoeGroupInfoTable 1 }

    EsPoeGroupInfoEntry ::= SEQUENCE {
        esPoeGroupMaxPorts  Integer32,
        esPoeGroupHWVersion DisplayString,
        esPoeGroupSWVersion DisplayString
    }

    esPoeGroupMaxPorts OBJECT-TYPE
        SYNTAX        Integer32
        MAX-ACCESS    read-only
        STATUS        current
        DESCRIPTION
             "This object indicates the maximum number of ports that the group
             can support."
        ::= { esPoeGroupInfoEntry 1 }

    esPoeGroupHWVersion OBJECT-TYPE
        SYNTAX        DisplayString
        MAX-ACCESS    read-only
        STATUS        current
        DESCRIPTION
             "This object indicates H/W version of PoE chip."
        ::= { esPoeGroupInfoEntry 2 }

    esPoeGroupSWVersion OBJECT-TYPE
        SYNTAX        DisplayString
        MAX-ACCESS    read-only
        STATUS        current
        DESCRIPTION
             "This object indicates firmware version of PoE chip."
        ::= { esPoeGroupInfoEntry 3 }

--------------------------------------------------------------------------------
    esPoeIfObjects  OBJECT IDENTIFIER ::= { esPoeMIBObjects 3 }

    esPoeIfCfgTable OBJECT-TYPE
        SYNTAX        SEQUENCE OF EsPoeIfCfgEntry
        MAX-ACCESS    not-accessible
        STATUS        current
        DESCRIPTION
             "This table consists of a list of PoE configuration
             information for ports."
        ::= { esPoeIfObjects 1 }

    esPoeIfCfgEntry OBJECT-TYPE
        SYNTAX        EsPoeIfCfgEntry
        MAX-ACCESS    not-accessible
        STATUS        current
        DESCRIPTION
             "An entry contains PoE configuration on a port."
        INDEX {
            pethMainPseGroupIndex,
            pethPsePortIndex
        }
        ::= { esPoeIfCfgTable 1 }

    EsPoeIfCfgEntry ::= SEQUENCE {
        esPoeIfState             INTEGER,
        esPoeIfMaxPower          Integer32,
        esPoeIfTimeRange         DisplayString,
        esPoeIfLegacyPdEnabled   TruthValue
    }

    esPoeIfState OBJECT-TYPE
        SYNTAX      INTEGER    {
           auto(1),
           never(2),
           static(3)
        }
        MAX-ACCESS      read-write
        STATUS          current
        DESCRIPTION
            "This object indicates the PoE state of the entry.
            auto(1) -  the port will automatically detect the PD and provision
                power to the PD. The max wattage value which can be provisioned
                to the port is determined by esPoeIfMaxPower. If esPoeIfMaxPower
                is unspecified, then the class of the PD auto determines the
                maximum wattage which can be provisioned. The PD will not be
                provisioned if it requests more wattage than the max wattage
                which is determined.
            never(2) - indicates the port will not supply power to connected PD;
            static(3) - indicates manager pre-allocate power budget to the port
                by configuring the esPoeIfMaxPower object. The power budget is allocated
                to the port even though there is no PD connected to the port.
                If esPoeIfMaxPower is not configured, default value is 15400mW for 802.3af
                and 30000mW for 802.3at."
        DEFVAL {auto}
        ::= { esPoeIfCfgEntry 1 }

    esPoeIfMaxPower OBJECT-TYPE
        SYNTAX          Integer32( 0 | 1000..30000)
        UNITS           "milliwatts"
        MAX-ACCESS      read-write
        STATUS           current
        DESCRIPTION
              "This object indicates the max wattage value which can
               be provisioned to the port.
               Note: This object is valid only while the esPoeIfState
               object is configured as auto or static."
        ::= { esPoeIfCfgEntry 2 }

    esPoeIfTimeRange OBJECT-TYPE
        SYNTAX          DisplayString (SIZE (0..32))
        MAX-ACCESS      read-write
        STATUS          current
        DESCRIPTION
              "This object indicates the name of time-range profile to delineate
               the activation period.
               A zero length string indicates the time-range is not specified.
               Note: This object is valid only while the esPoeIfState is 'auto'."
        ::= { esPoeIfCfgEntry 3 }

    esPoeIfLegacyPdEnabled OBJECT-TYPE
        SYNTAX        TruthValue
        MAX-ACCESS    read-write
        STATUS        current
        DESCRIPTION
            "This object indicates the state of legacy PD support."
        DEFVAL { false }
        ::= { esPoeIfCfgEntry 4 }

--------------------------------------------------------------------------------
    esPoeIfInfoObjects  OBJECT IDENTIFIER ::= { esPoeIfObjects 2 }

    esPoeIfStatusTable OBJECT-TYPE
        SYNTAX        SEQUENCE OF EsPoeIfStatusEntry
        MAX-ACCESS    not-accessible
        STATUS        current
        DESCRIPTION
             "This table consists of a list of PoE status for ports."
        ::= { esPoeIfInfoObjects 1 }

    esPoeIfStatusEntry  OBJECT-TYPE
        SYNTAX          EsPoeIfStatusEntry
        MAX-ACCESS      not-accessible
        STATUS          current
        DESCRIPTION
             "An entry consists of PoE status for a port."
        INDEX { pethMainPseGroupIndex,pethPsePortIndex }
        ::= { esPoeIfStatusTable 1 }

    EsPoeIfStatusEntry ::= SEQUENCE {
        esPoeIfDetectStatus             INTEGER,
        esPoeIfFaultyType               INTEGER,
        esPoeIfPowerClassifications     INTEGER,
        esPoeIfOperMaxPower             Unsigned32,
        esPoeIfOperOutputPower          Unsigned32,
        esPoeIfOperDescription          DisplayString
    }

    esPoeIfDetectStatus OBJECT-TYPE
        SYNTAX          INTEGER {
            disabled(1),
            searching(2),
            requesting(3),
            delivering(4),
            faulty(5)
        }
        MAX-ACCESS      read-only
        STATUS          current
        DESCRIPTION
             "This object indicates the operational status of the port PD detection.
             disabled(1) - PSE function is disabled.
             searching(2) - Remote PD is not connected.
             requesting(3) - Remote PD is inserted, but the PSE doesn't provide power yet.
             delivering(4) - Remote PD is now powering by PoE system.
             faulty(5) - Device detection or a powered device is in a faulty state.
             "
        ::= { esPoeIfStatusEntry 1 }

    esPoeIfFaultyType OBJECT-TYPE
        SYNTAX        INTEGER {
            notApplicable(0),
            mpsAbsent(1),
            pdShort(2),
            overload(3),
            powerDenied(4),
            thermalShutdown(5),
            startupFailure(6),
            classificationFailure(7)
        }
        MAX-ACCESS    read-only
        STATUS        current
        DESCRIPTION
            "This object indicates the specific faulty type. It is meaningful
            only when esPoeIfDetectStatus object is 'faulty'.
            notApplicable(0) - indicates this object is meaningless, e.g. the
                esPoeIfDetectStatus is not 'faulty'.
            mpsAbsent(1) - indicates MPS(Maintain Power Signature) Absent
            pdShort(2) - indicates PD Short
            overload(3) - indicates Overload
            powerDenied(4) - indicates Power Denied
            thermalShutdown(5)- indicates Thermal Shutdown
            startupFailure(6) -  indicates Startup Failure
            classificationFailure(7) - indicates Classification Failure(IEEE 802.3at)
            "
        ::= { esPoeIfStatusEntry 2 }

    esPoeIfPowerClassifications OBJECT-TYPE
         SYNTAX INTEGER   {
                none(0),
                class0(1),
                class1(2),
                class2(3),
                class3(4),
                class4(5)
         }
        MAX-ACCESS read-only
        STATUS current
        DESCRIPTION
            "Classification is a way to tag different terminals on the
            Power over LAN network according to their power consumption.
            Devices such as IP telephones, WLAN access points and others,
            will be classified according to their power requirements.

            The meaning of the classification labels is defined in the
            IEEE specification.

           This variable is valid only while a PD is being powered,
            that is, while the attribute pethPsePortDetectionStatus
            is reporting the enumeration deliveringPower."
       ::= { esPoeIfStatusEntry 3 }

    esPoeIfOperMaxPower OBJECT-TYPE
        SYNTAX          Unsigned32
        MAX-ACCESS      read-only
        STATUS          current
        DESCRIPTION
            "This object indicates the maximum power of the port."
        ::= { esPoeIfStatusEntry 4 }

    esPoeIfOperOutputPower OBJECT-TYPE
        SYNTAX          Unsigned32
        UNITS           "milliwatts"
        MAX-ACCESS      read-only
        STATUS          current
        DESCRIPTION
            "This object indicates the output power of the port."
        ::= { esPoeIfStatusEntry 5 }

    esPoeIfOperDescription OBJECT-TYPE
        SYNTAX          DisplayString
        MAX-ACCESS      read-only
        STATUS          current
        DESCRIPTION
              "This object indicates the description for the port."
        ::= { esPoeIfStatusEntry 6 }

--------------------------------------------------------------------------------
    esPoeIfMeasurementTable OBJECT-TYPE
        SYNTAX          SEQUENCE OF EsPoeIfMeasurementEntry
        MAX-ACCESS      not-accessible
        STATUS          current
        DESCRIPTION
            "This table consists of a list of POE measurement
            information for ports."
        ::= { esPoeIfInfoObjects 2 }

    esPoeIfMeasurementEntry  OBJECT-TYPE
        SYNTAX          EsPoeIfMeasurementEntry
        MAX-ACCESS      not-accessible
        STATUS          current
        DESCRIPTION
             "An entry consists of PoE measurement information of a port."
        INDEX {
            pethMainPseGroupIndex,
            pethPsePortIndex
        }
        ::= { esPoeIfMeasurementTable 1 }

    EsPoeIfMeasurementEntry ::= SEQUENCE {
        esPoeIfVoltage           Integer32,
        esPoeIfCurrent           Integer32,
        esPoeIfTemperature       Integer32,
        esPoeIfPower             Integer32
    }

    esPoeIfVoltage OBJECT-TYPE
        SYNTAX        Integer32
        UNITS         "millivolts"
        MAX-ACCESS    read-only
        STATUS        current
        DESCRIPTION
            "This object indicates the voltage of the port in millivolts."
        ::= { esPoeIfMeasurementEntry 1 }

     esPoeIfCurrent OBJECT-TYPE
        SYNTAX        Integer32
        UNITS         "milliamperes"
        MAX-ACCESS    read-only
        STATUS        current
        DESCRIPTION
             "This object indicates the current of port in milliamperes."
        ::= { esPoeIfMeasurementEntry 2 }

     esPoeIfTemperature OBJECT-TYPE
        SYNTAX        Integer32
        UNITS         "Degree Centigrade"
        MAX-ACCESS    read-only
        STATUS        current
        DESCRIPTION
             "This object indicates the temperature of port in degrees centigrade."
        ::= { esPoeIfMeasurementEntry 3 }

     esPoeIfPower OBJECT-TYPE
        SYNTAX        Integer32
        MAX-ACCESS    read-only
        STATUS        current
        DESCRIPTION
             "This object indicates consumption power of port in milliwatts."
        ::= { esPoeIfMeasurementEntry 4 }

--------------------------------------------------------------------------------
    esPoeIfStatisticsTable  OBJECT-TYPE
        SYNTAX          SEQUENCE OF EsPoeIfStatisticsEntry
        MAX-ACCESS      not-accessible
        STATUS          current
        DESCRIPTION
            "This table consists of a list of POE statistics
            information for ports."
        ::= { esPoeIfInfoObjects 3 }

    esPoeIfStatisticsEntry  OBJECT-TYPE
        SYNTAX          EsPoeIfStatisticsEntry
        MAX-ACCESS      not-accessible
        STATUS          current
        DESCRIPTION
             "An entry consists of PoE statistics information of a port."
        INDEX {
            pethMainPseGroupIndex,
            pethPsePortIndex
        }
        ::= { esPoeIfStatisticsTable 1 }

    EsPoeIfStatisticsEntry ::= SEQUENCE {
        esPoeIfStatMpsAbsent            Integer32,
        esPoeIfStatOverload             Integer32,
        esPoeIfStatShort                Integer32,
        esPoeIfStatPowerDenied          Integer32,
        esPoeIfStatInvalidSignature     Integer32
    }

    esPoeIfStatMpsAbsent OBJECT-TYPE
        SYNTAX        Integer32
        MAX-ACCESS    read-only
        STATUS        current
        DESCRIPTION
            "This object indicates the MPS absent counter."
        ::= { esPoeIfStatisticsEntry 1 }

     esPoeIfStatOverload OBJECT-TYPE
        SYNTAX        Integer32
        MAX-ACCESS    read-only
        STATUS        current
        DESCRIPTION
             "This object indicates the overload counter."
        ::= { esPoeIfStatisticsEntry 2 }

     esPoeIfStatShort OBJECT-TYPE
        SYNTAX        Integer32
        MAX-ACCESS    read-only
        STATUS        current
        DESCRIPTION
             "This object indicates the short counter."
        ::= { esPoeIfStatisticsEntry 3 }

     esPoeIfStatPowerDenied OBJECT-TYPE
        SYNTAX        Integer32
        MAX-ACCESS    read-only
        STATUS        current
        DESCRIPTION
             "This object indicates the power denied counter."
        ::= { esPoeIfStatisticsEntry 4 }

    esPoeIfStatInvalidSignature OBJECT-TYPE
        SYNTAX        Integer32
        MAX-ACCESS    read-only
        STATUS        current
        DESCRIPTION
             "This object indicates the invalid signature counter."
        ::= { esPoeIfStatisticsEntry 5 }

--------------------------------------------------------------------------------
    esPoeIfPdAliveCfgTable OBJECT-TYPE
        SYNTAX        SEQUENCE OF EsPoeIfPdAliveCfgEntry
        MAX-ACCESS    not-accessible
        STATUS        current
        DESCRIPTION
             "This table consists of a list of configuration for the PD
             alive check function for ports.
             The PD alive check feature provides the solution for
             PD device that has the stop working or no response
             problem via Ping mechanism.
             Detailed Process:
             The detailed processes are described as follows:
             1. The system  needs to  periodically monitor the
              specific PD by using Ping function. If there is no
              response, system takes one of the following actions:
              (1) Reset: Switch resets (disable then enable) PoE
                  power on the port which connects to a PD under monitoring.
              (2) Notify: Switch sends logs and traps to notify the administrator.
              (3) Both: Switch sends logs and traps, and resets the PoE port power.
             2. The system should implement the retry  mechanism to check
              PD aliveness, hence the system will reset the PoE port power
              feeding after the retry by using Ping without any response from a PD.
             3. If the action is Reset or  Both, the system needs
              to wait for PD recovery from rebooting and then executes
              the Ping function again. Besides, the waiting time can
              be configured by users.
             4. If PoE schedule (time range) function is configured
              on the port which enables the PD Alive Check  function,
              the time range function has the top priority, and
              therefore PD Alive Check function will not work
              while PoE time range function is still active.
             5. This function only takes effect on PoE enabled
              port with power feeding.

             Note: It is required to setup IP settings properly that
              the PD can be reachable for Ping, otherwise this function
              cannot work as expected.

              Limitation
             1. Support Ping Function: If the PD does not support ICMP,
              this function cannot work normally.
             2. Direct-Connected PD: The Reset Action can only work on
              the direct-connected PD. If the PD is not connected directly,
              the Reset Action may not work as expected.
             3. PD Also Acts as PSE: If the direct-connected PD is also a PSE,
              all the next level PDs connect to this PSE will be power cycling
              whenever PD Alive Check function takes effect on 'Reset' or 'Both' Action."
        ::= { esPoeIfObjects 3 }

    esPoeIfPdAliveCfgEntry OBJECT-TYPE
        SYNTAX        EsPoeIfPdAliveCfgEntry
        MAX-ACCESS    not-accessible
        STATUS        current
        DESCRIPTION
             "An entry contains configuration for PD alive check on a port."
        INDEX {
            pethMainPseGroupIndex,
            pethPsePortIndex
        }
        ::= { esPoeIfPdAliveCfgTable 1 }

    EsPoeIfPdAliveCfgEntry ::= SEQUENCE {
        esPoeIfPdAliveCfgState           INTEGER,
        esPoeIfPdAliveCfgPdIpType        InetAddressType,
        esPoeIfPdAliveCfgPdIpAddr        InetAddress,
        esPoeIfPdAliveCfgInterval        Unsigned32,
        esPoeIfPdAliveCfgRetry           Unsigned32,
        esPoeIfPdAliveCfgWaitTime        Unsigned32,
        esPoeIfPdAliveCfgAction          INTEGER,
        esPoeIfPdAliveCfgResidentialVlan VlanId
    }

    esPoeIfPdAliveCfgState OBJECT-TYPE
        SYNTAX          INTEGER    {
                           enabled(1),
                           disabled(2)
                        }
        MAX-ACCESS      read-write
        STATUS          current
        DESCRIPTION
            "This object indicates the the PD alive function sate.
             enabled - Enable the PD alive check function
             disabled - Disable the PD alive check function."
        DEFVAL { disabled }
        ::= { esPoeIfPdAliveCfgEntry 1 }

    esPoeIfPdAliveCfgPdIpType OBJECT-TYPE
        SYNTAX          InetAddressType
        MAX-ACCESS      read-write
        STATUS          current
        DESCRIPTION
            "This object indicates the IP address type of the target PD."
        ::= { esPoeIfPdAliveCfgEntry 2 }

    esPoeIfPdAliveCfgPdIpAddr OBJECT-TYPE
        SYNTAX          InetAddress
        MAX-ACCESS      read-write
        STATUS          current
        DESCRIPTION
            "This object indicates the IP address of the target PD."
        ::= { esPoeIfPdAliveCfgEntry 3 }

    esPoeIfPdAliveCfgInterval OBJECT-TYPE
        SYNTAX          Unsigned32 (10..300)
        UNITS           "seconds"
        MAX-ACCESS      read-write
        STATUS          current
        DESCRIPTION
              "This object indicates the time interval for system
               issues ping request to detect the target PD.
               The valid range for interval time is 10s to 300s."
        DEFVAL { 30 }
        ::= { esPoeIfPdAliveCfgEntry 4 }

    esPoeIfPdAliveCfgRetry OBJECT-TYPE
        SYNTAX          Unsigned32 (0..5)
        UNITS           "times"
        MAX-ACCESS      read-write
        STATUS          current
        DESCRIPTION
              "This object indicates the retry count of ping
               request when PD has no response.
               The valid range for retry count is 0 to 5 times."
        DEFVAL { 2}
        ::= { esPoeIfPdAliveCfgEntry 5 }


    esPoeIfPdAliveCfgWaitTime OBJECT-TYPE
        SYNTAX          Unsigned32 (30..300)
        UNITS           "seconds"
        MAX-ACCESS      read-write
        STATUS          current
        DESCRIPTION
              "This object indicates the waiting time for PD reboot.
              The valid range for waiting time is 30s to 300s."
        DEFVAL { 90 }
        ::= { esPoeIfPdAliveCfgEntry 6 }

    esPoeIfPdAliveCfgAction OBJECT-TYPE
        SYNTAX          INTEGER {
                           reset(1),
                           notify(2),
                           both(3)
                        }
        MAX-ACCESS      read-write
        STATUS          current
        DESCRIPTION
              "This object indicates the action when PD doesn't reply the ping request.
               reset- System will reset the PoE port state .
               notify- System will send log and trap to notify the administrator.
               both- System will send log and trap first and reset the PoE port state."
        DEFVAL { both }
        ::= { esPoeIfPdAliveCfgEntry 7 }
        
    esPoeIfPdAliveCfgResidentialVlan OBJECT-TYPE
        SYNTAX          VlanId
        MAX-ACCESS      read-write
        STATUS          current
        DESCRIPTION
              "This object indicates the VLAN identifier (VID) of the source IP interface dedicated for ICMP messages. 
               The specific VID of the IP interface is only used for IPv6 ICMP messages."
        ::= { esPoeIfPdAliveCfgEntry 8 }
    

-- *****************************************************************************
-- MIB Notifications
-- *****************************************************************************
    esPoeIfPowerDeniedNotification  NOTIFICATION-TYPE
         OBJECTS    { pethPsePortPowerDeniedCounter }
         STATUS      current
         DESCRIPTION
             " This Notification indicates if PSE state diagram enters
               the state POWER_DENIED.
               At least 500 msec must elapse between notifications
               being emitted by the same object instance."
          ::= { esPoeMIBNotifications 1 }

    esPoeIfPowerOverLoadNotification  NOTIFICATION-TYPE
         OBJECTS     { pethPsePortOverLoadCounter }
         STATUS      current
         DESCRIPTION
             " This Notification indicates if PSE state diagram enters
               the state ERROR_DELAY_OVER.
               At least 500 msec must elapse between notifications
               being emitted by the same object instance."
          ::= { esPoeMIBNotifications 2 }

    esPoeIfPowerShortCircuitNotification  NOTIFICATION-TYPE
         OBJECTS     { pethPsePortShortCounter }
         STATUS      current
         DESCRIPTION
             " This Notification indicates if PSE state diagram enters
               the state ERROR_DELAY_SHORT.
               At least 500 msec must elapse between notifications
               being emitted by the same object instance."
          ::= { esPoeMIBNotifications 3 }

    esPoeIfPdAliveFailOccurNotification  NOTIFICATION-TYPE
         OBJECTS     { pethMainPseGroupIndex,
                       pethPsePortIndex,
                       esPoeIfPdAliveCfgPdIpType,
                       esPoeIfPdAliveCfgPdIpAddr
                     }
         STATUS      current
         DESCRIPTION
             " This Notification indicates if the PD device has
               the stop working or no response problem."
          ::= { esPoeMIBNotifications 4 }

-- *****************************************************************************
-- MIB Conformance statements
-- *****************************************************************************
    esPoeMIBCompliances  OBJECT IDENTIFIER  ::= { esPoeMIBConformance 1 }

    esPoeMIBGroups  OBJECT IDENTIFIER  ::= { esPoeMIBConformance 2 }
    esPoeMIBCompliance MODULE-COMPLIANCE
        STATUS          current
        DESCRIPTION
            "The compliance statement for entities which implement the
             DLINKES-POE-MIB."
        MODULE          -- this module
        MANDATORY-GROUPS {
            esPoeGroupCfgGroup,
            esPoeIfCfgGroup,
            esPoeGroupInfoGroup,
            esPoeIfInfoGroup,
            esPoeIfErrorStateNotificationGroup,
            esPoeIfPdAliveCfgGroup
        }

        ::= { esPoeMIBCompliances 1 }

    esPoeGroupCfgGroup OBJECT-GROUP
        OBJECTS {
             esPoeGroupPolicyPreempt,
             esPoeGroupGuardBand,
             esPoeGroupPerpetual
        }
        STATUS current
        DESCRIPTION
            "A collection of objects to configure or display the group-specific
            PoE information."
        ::= { esPoeMIBGroups 1 }

    esPoeIfCfgGroup OBJECT-GROUP
        OBJECTS {
             esPoeGroupClearIfStatistic,
             esPoeIfState,
             esPoeIfMaxPower,
             esPoeIfTimeRange,
             esPoeIfLegacyPdEnabled
        }
        STATUS current
        DESCRIPTION
            "A collection of objects configure or display the ports information."
        ::= { esPoeMIBGroups 2 }

    esPoeGroupInfoGroup OBJECT-GROUP
        OBJECTS {
             esPoeGroupMaxPorts,
             esPoeGroupHWVersion,
             esPoeGroupSWVersion
        }
        STATUS current
        DESCRIPTION
            "A collection of objects display the groups information."
        ::= { esPoeMIBGroups 3 }

    esPoeIfInfoGroup OBJECT-GROUP
        OBJECTS {
            esPoeIfDetectStatus,
            esPoeIfFaultyType,
            esPoeIfPowerClassifications,
            esPoeIfOperMaxPower,
            esPoeIfOperOutputPower,
            esPoeIfOperDescription,
            esPoeIfVoltage,
            esPoeIfCurrent,
            esPoeIfTemperature,
            esPoeIfPower,
            esPoeIfStatMpsAbsent,
            esPoeIfStatOverload,
            esPoeIfStatShort,
            esPoeIfStatPowerDenied,
            esPoeIfStatInvalidSignature
        }
        STATUS current
        DESCRIPTION
            "A collection of objects display the ports information."
        ::= { esPoeMIBGroups 4 }

    esPoeIfErrorStateNotificationGroup NOTIFICATION-GROUP
        NOTIFICATIONS  {
                         esPoeIfPowerDeniedNotification,
                         esPoeIfPowerOverLoadNotification,
                         esPoeIfPowerShortCircuitNotification,
                         esPoeIfPdAliveFailOccurNotification
                       }
        STATUS         current
        DESCRIPTION
            "A collection of objects provides ports error state notifications."
        ::= { esPoeMIBGroups 5 }

    esPoeIfPdAliveCfgGroup OBJECT-GROUP
        OBJECTS        {
                         esPoeIfPdAliveCfgState,
                         esPoeIfPdAliveCfgPdIpType,
                         esPoeIfPdAliveCfgPdIpAddr,
                         esPoeIfPdAliveCfgInterval,
                         esPoeIfPdAliveCfgRetry,
                         esPoeIfPdAliveCfgWaitTime,
                         esPoeIfPdAliveCfgAction,
                         esPoeIfPdAliveCfgResidentialVlan
                       }
        STATUS         current
        DESCRIPTION
            "A collection of objects display the PD alive check configuration."
        ::= { esPoeMIBGroups 6 }

END
