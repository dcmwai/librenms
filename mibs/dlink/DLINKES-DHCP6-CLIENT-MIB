--  *****************************************************************
--  DLINKES-DHCP6-CLIENT-MIB.mib : DHCPv6 Client MIB
-- 
--  Copyright (c) 2013 D-Link Corporation, all rights reserved.
--   
--  *****************************************************************
DLINKES-DHCP6-CLIENT-MIB DEFINITIONS ::= BEGIN

    IMPORTS
        MODULE-IDENTITY,
        OBJECT-TYPE,
        Integer32,
        Unsigned32        
                FROM SNMPv2-SMI
        DisplayString,
        TruthValue,
        RowStatus
            FROM SNMPv2-TC
        MODULE-COMPLIANCE, OBJECT-GROUP
		    FROM SNMPv2-CONF 
        InterfaceIndex,
        InterfaceIndexOrZero
            FROM IF-MIB
        InetAddressPrefixLength, InetAddressIPv6
            FROM INET-ADDRESS-MIB
        dlinkCommon			
			FROM DLINK-ID-REC-MIB;


    dlinkEsDhcp6ClientMIB MODULE-IDENTITY
        LAST-UPDATED "201301180000Z"
        ORGANIZATION "D-Link Corp."
        CONTACT-INFO
            "         D-Link Corporation
             Postal: No. 289, Sinhu 3rd Rd., Neihu District,
                     Taipei City 114, Taiwan, R.O.C
             Tel:    +886-2-66000123
             E-mail: tsd@dlink.com.tw
            "
        DESCRIPTION
            "This MIB module defines objects for DHCPv6 Client."
        REVISION     "201301180000Z"
        DESCRIPTION
            "This is the first version of the MIB file for 'DHCPv6 Client'
            functionality."
        ::= { dlinkCommon 222 }

-- -----------------------------------------------------------------------------
    esDhcp6ClientNotifications    OBJECT IDENTIFIER ::= { dlinkEsDhcp6ClientMIB 0 }
    esDhcp6ClientObjects          OBJECT IDENTIFIER ::= { dlinkEsDhcp6ClientMIB 1 }
    esDhcp6ClientConformance      OBJECT IDENTIFIER ::= { dlinkEsDhcp6ClientMIB 2 }

-- -----------------------------------------------------------------------------
    esDhcp6ClientGeneral          OBJECT IDENTIFIER ::= { esDhcp6ClientObjects 1 }

    esDhcp6ClientDuid OBJECT-TYPE
        SYNTAX      OCTET STRING
        MAX-ACCESS  read-only
        STATUS      current
        DESCRIPTION
            "The DHCP Unique Identity (DUID) of DHCPv6 Client."
        ::= { esDhcp6ClientGeneral 1 }
 
    dhcp6ClientRestartIf OBJECT-TYPE
        SYNTAX      InterfaceIndexOrZero
        MAX-ACCESS  read-write
        STATUS      current
        DESCRIPTION
            "Specifies the ifIndex of the interface on which DHCPv6 client will
            be restart.
            The agent will return an inconsistentValue error on sets if DHCPv6
            client is not enabled on the interface.         	            
            The special value 0 is return when read."
        ::= { esDhcp6ClientGeneral 2 }


-- -----------------------------------------------------------------------------
    esDhcp6ClientIfObjects          OBJECT IDENTIFIER ::= { esDhcp6ClientObjects 2 }
    esDhcp6CIfTable OBJECT-TYPE
        SYNTAX          SEQUENCE OF EsDhcp6CIfEntry
        MAX-ACCESS      not-accessible
        STATUS          current
        DESCRIPTION
             "A table contains all DHCPv6 client entries which consists of
             DHCPv6 client related configuration. An entry is created to set a
             value different from the default on an interface. If an entry is
             deleted, all configurations are reverted to default."
        ::= { esDhcp6ClientIfObjects 1 }

    esDhcp6CIfEntry OBJECT-TYPE
        SYNTAX          EsDhcp6CIfEntry
        MAX-ACCESS      not-accessible
        STATUS          current
        DESCRIPTION
            "Defines an entry in the esDhcp6CIfTable."
        INDEX  { esDhcp6CIfIndex }
        ::= { esDhcp6CIfTable 1 }

    EsDhcp6CIfEntry ::= SEQUENCE {
        esDhcp6CIfIndex                  InterfaceIndex, 
        esDhcp6CIfAcquireAddrEnabled     TruthValue,   
        esDhcp6CIfAcqAddrRapidCommit     TruthValue, 
        esDhcp6CIfMinRefresh             Unsigned32,
        esDhcp6CIfRowStatus              RowStatus
    }

    esDhcp6CIfIndex  OBJECT-TYPE
        SYNTAX          InterfaceIndex
        MAX-ACCESS      not-accessible
        STATUS          current
        DESCRIPTION
            "The ifIndex value of the interface.
            Only VLAN interfaces are valid interfaces."
        ::= { esDhcp6CIfEntry 1 }
        
    esDhcp6CIfAcquireAddrEnabled OBJECT-TYPE
        SYNTAX          TruthValue
        MAX-ACCESS      read-create
        STATUS          current
        DESCRIPTION
            "This object indicates whether acquires an IPv6 address on an
            interface from the DHCPv6 server." 
        DEFVAL      { false }    
        ::= { esDhcp6CIfEntry 2 }
           
    esDhcp6CIfAcqAddrRapidCommit OBJECT-TYPE
        SYNTAX          TruthValue
        MAX-ACCESS      read-create
        STATUS          current
        DESCRIPTION
            "This object indicates whether the two-message
            exchange for address allocation and other configuration is used.
            When esDhcp6CIfAcquireAddrEnabled is 'false', esDhcp6CIfRapidCommit
            cannot be set to 'true'." 
        DEFVAL      { false }    
        ::= { esDhcp6CIfEntry 3 }
     
    esDhcp6CIfMinRefresh OBJECT-TYPE
        SYNTAX          Unsigned32 (600..4294967295)
        MAX-ACCESS      read-create
        STATUS          current
        DESCRIPTION
            "This object specifies the minimum acceptable information refresh 
            time in seconds. If the client receives a information refresh time
            less than the configured minimum refresh time, the configured 
            minimum refresh time will be used."
        DEFVAL      { 86400 }
        ::= { esDhcp6CIfEntry 4 }
                    
     esDhcp6CIfRowStatus OBJECT-TYPE
        SYNTAX          RowStatus
        MAX-ACCESS      read-create
        STATUS          current
        DESCRIPTION
           "The status of this conceptual row." 
        ::= { esDhcp6CIfEntry 5 } 
                 
-- -----------------------------------------------------------------------------   	
   	 esDhcp6CIfPrefixDeleCfgTable OBJECT-TYPE
        SYNTAX          SEQUENCE OF EsDhcp6CIfPrefixDeleCfgEntry
        MAX-ACCESS      not-accessible
        STATUS          current
        DESCRIPTION
             "The table contains information about prefix delegation request 
             of DHCPv6 client. An entry is created/removed when enable/disable
             request for prefix delegation through a specified interface."
        ::= { esDhcp6ClientIfObjects 3 }

    esDhcp6CIfPrefixDeleCfgEntry OBJECT-TYPE
        SYNTAX          EsDhcp6CIfPrefixDeleCfgEntry
        MAX-ACCESS      not-accessible
        STATUS          current
        DESCRIPTION
            "Defines an entry in the esDhcp6CIfPrefixDeleCfgTable."
        INDEX  { esDhcp6CIfPdCfgIfIndex }
        ::= { esDhcp6CIfPrefixDeleCfgTable 1 }

    EsDhcp6CIfPrefixDeleCfgEntry ::= SEQUENCE {
        esDhcp6CIfPdCfgIfIndex      InterfaceIndex,              
        esDhcp6CIfPdCfgPrefixName   DisplayString,
        esDhcp6CIfPdCfgHintAddr     InetAddressIPv6,
        esDhcp6CIfPdCfgHintLen      InetAddressPrefixLength,
        esDhcp6CIfPdCfgRapidCommit  TruthValue,
        esDhcp6CIfPdCfgRowStatus    RowStatus
    }
    
    esDhcp6CIfPdCfgIfIndex  OBJECT-TYPE
        SYNTAX          InterfaceIndex
        MAX-ACCESS      not-accessible
        STATUS          current
        DESCRIPTION
            "The ifIndex value of the interface.
             Only VLAN interfaces are valid interfaces."
        ::= { esDhcp6CIfPrefixDeleCfgEntry 1 }
        
    esDhcp6CIfPdCfgPrefixName OBJECT-TYPE
        SYNTAX          DisplayString (SIZE (0..32))
        MAX-ACCESS      read-create
        STATUS          current
        DESCRIPTION
            "This object indicates a IPv6 general prefix name.           
            The prefix acquired from the server will be stored in the IPv6
            general prefix pool represented by this object, which will be in
            turn used in configuration of IPv6 addresses.
            The zero length indicates the general prefix name is not configured.
            Either esDhcp6CIfPdCfgPrefixName or esDhcp6CIfPdCfgHintAddr can be configured
            on an interface.
            If neither esDhcp6CIfPdCfgPrefixName nor esDhcp6CIfPdCfgHintAddr is 
            configured, this indicates the request for prefix delegation
            through a specified interface is disabled and the entry will be
            deleted."
        ::= { esDhcp6CIfPrefixDeleCfgEntry 2 }
        
    esDhcp6CIfPdCfgHintAddr OBJECT-TYPE
        SYNTAX          InetAddressIPv6
        MAX-ACCESS      read-create
        STATUS          current
        DESCRIPTION
            "This object indicates an IPv6 prefix to be sent in the prefix
            delegation request message as a hint.
            The special value of all '00'Hs indicates that hint IPv6 prefix is 
            not configured.
            Either esDhcp6CIfPdCfgPrefixName or esDhcp6CIfPdCfgHintAddr can be configured
            on an interface.
            If neither esDhcp6CIfPdCfgPrefixName nor esDhcp6CIfPdCfgHintAddr is  
            configured, this indicates the request for prefix delegation
            through a specified interface is disabled and the entry will be
            deleted."           
        ::= { esDhcp6CIfPrefixDeleCfgEntry 3 }

    esDhcp6CIfPdCfgHintLen OBJECT-TYPE
        SYNTAX          InetAddressPrefixLength 
        MAX-ACCESS      read-create
        STATUS          current
        DESCRIPTION
            "The length of the prefix (in bits).
             It indicates the length of hint prefix."
        ::= { esDhcp6CIfPrefixDeleCfgEntry 4 }
 
    esDhcp6CIfPdCfgRapidCommit OBJECT-TYPE
        SYNTAX          TruthValue
        MAX-ACCESS      read-create
        STATUS          current
        DESCRIPTION
            "This object indicates that whether proceed with two-message
            exchange for prefix delegation.  The rapid-commit option will be
            filled in the Solicit message to request two messages handshake." 
        ::= { esDhcp6CIfPrefixDeleCfgEntry 5 }
   	
   	 esDhcp6CIfPdCfgRowStatus OBJECT-TYPE
        SYNTAX      RowStatus
        MAX-ACCESS  read-create
        STATUS      current
        DESCRIPTION
           "The status of this conceptual row." 
        ::= { esDhcp6CIfPrefixDeleCfgEntry 6 }
        		
-- -----------------------------------------------------------------------------
    esDhcp6ClientStatusObjects    OBJECT IDENTIFIER ::= { esDhcp6ClientObjects 3 }
    
    esDhcp6CIfStateTable OBJECT-TYPE
        SYNTAX          SEQUENCE OF EsDhcp6CIfStateEntry
        MAX-ACCESS      not-accessible
        STATUS          current
        DESCRIPTION
             "The table contains per-interface DHCPv6 client state information."
        ::= { esDhcp6ClientStatusObjects 1 }

    esDhcp6CIfStateEntry OBJECT-TYPE
        SYNTAX      EsDhcp6CIfStateEntry
        MAX-ACCESS  not-accessible
        STATUS      current
        DESCRIPTION
            "Defines an entry in the esDhcp6CIfStateTable."
        INDEX  { esDhcp6CIfStateIfIndex }
        ::= { esDhcp6CIfStateTable 1 }

    EsDhcp6CIfStateEntry ::= SEQUENCE {
            esDhcp6CIfStateIfIndex       InterfaceIndex,
            esDhcp6CIfStateCode          INTEGER,
            esDhcp6CIfStatusEventExpire  Unsigned32              
        }
        
    esDhcp6CIfStateIfIndex OBJECT-TYPE
        SYNTAX      InterfaceIndex
        MAX-ACCESS  not-accessible
        STATUS      current
        DESCRIPTION
            "The ifIndex value of the interface.
             Only VLAN interfaces are valid interfaces."
        ::= { esDhcp6CIfStateEntry 1 }
        
    esDhcp6CIfStateCode OBJECT-TYPE
        SYNTAX      INTEGER { invalid(0), init(1), request(2),
                              release(3), active(4), renew(5), rebind(6) }
        MAX-ACCESS  read-only
        STATUS      current
        DESCRIPTION
            "DHCPv6 Client running state."
        ::= { esDhcp6CIfStateEntry 2 }
     
    esDhcp6CIfStatusEventExpire OBJECT-TYPE
        SYNTAX      Unsigned32
        MAX-ACCESS  read-only
        STATUS      current
        DESCRIPTION
            "Next event expire time of DHCPv6 Client.
             It is valid when DHCPv6 Client in 
             REQUEST and REBIND state."
        ::= { esDhcp6CIfStateEntry 3 }
        
-- -----------------------------------------------------------------------------    
    esDhcp6CIfAcquiredIaTable OBJECT-TYPE
        SYNTAX          SEQUENCE OF EsDhcp6CIfAcquiredIaEntry
        MAX-ACCESS      not-accessible
        STATUS          current
        DESCRIPTION
             "The table contains the list of the known DHCPv6 servers."
        ::= { esDhcp6ClientStatusObjects 2 }

    esDhcp6CIfAcquiredIaEntry OBJECT-TYPE
        SYNTAX      EsDhcp6CIfAcquiredIaEntry
        MAX-ACCESS  not-accessible
        STATUS      current
        DESCRIPTION
            "Defines an entry in the esDhcp6CIfAcquiredIaTable."
        INDEX  { 
            esDhcp6CIfAcquiredIaType,
            esDhcp6CIfAcquiredIaId,
            esDhcp6CIfAcquiredIaIfIndex }
        ::= { esDhcp6CIfAcquiredIaTable 1 }

    EsDhcp6CIfAcquiredIaEntry ::= SEQUENCE {                  
            esDhcp6CIfAcquiredIaType             INTEGER,
            esDhcp6CIfAcquiredIaId               Unsigned32,
            esDhcp6CIfAcquiredIaIfIndex          InterfaceIndex,      
            esDhcp6CIfAcquiredIaServerAddr       InetAddressIPv6,
            esDhcp6CIfAcquiredIaServerDUID       OCTET STRING,
            esDhcp6CIfAcquiredIaServerPref       Unsigned32,                  
            esDhcp6CIfAcquiredIaT1               Unsigned32,
            esDhcp6CIfAcquiredIaT2               Unsigned32,            
            esDhcp6CIfAcquiredIaExpireTime       Unsigned32         
        }
   
    esDhcp6CIfAcquiredIaType OBJECT-TYPE
        SYNTAX          INTEGER { other(0), iapd(1), iana(2) }
        MAX-ACCESS      not-accessible
        STATUS          current
        DESCRIPTION
            "The acquired IA type.
             other(0) - none of the following.
             iapd(1)  - the type of the IA is Prefix Delegation.
             iana(2)  - the type of the IA is non-temporary addresses."             
        ::= { esDhcp6CIfAcquiredIaEntry 1 }

    esDhcp6CIfAcquiredIaId OBJECT-TYPE
        SYNTAX          Unsigned32 (0..4294967295)
        MAX-ACCESS      not-accessible
        STATUS          current
        DESCRIPTION
            "The acquired IA identify."
        ::= { esDhcp6CIfAcquiredIaEntry 2 }

     esDhcp6CIfAcquiredIaIfIndex OBJECT-TYPE
        SYNTAX          InterfaceIndex
        MAX-ACCESS      not-accessible
        STATUS          current
        DESCRIPTION
            "The ifIndex value of the interface.
            Only VLAN interfaces are valid interfaces."
        ::= { esDhcp6CIfAcquiredIaEntry 3 }
      
    esDhcp6CIfAcquiredIaServerAddr OBJECT-TYPE
        SYNTAX          InetAddressIPv6
        MAX-ACCESS      read-only
        STATUS          current
        DESCRIPTION
            "The address of DHCPv6 server."
        ::= { esDhcp6CIfAcquiredIaEntry 4 }
                
    esDhcp6CIfAcquiredIaServerDUID OBJECT-TYPE
        SYNTAX          OCTET STRING
        MAX-ACCESS      read-only
        STATUS          current
        DESCRIPTION
            "The DUID of the corresponding DHCPv6 server."
        ::= { esDhcp6CIfAcquiredIaEntry 5 }

    esDhcp6CIfAcquiredIaServerPref OBJECT-TYPE
        SYNTAX          Unsigned32 (0..4294967295)
        MAX-ACCESS      read-only
        STATUS          current
        DESCRIPTION
            "The preference of the corresponding DHCPv6 server."
        ::= { esDhcp6CIfAcquiredIaEntry 6 }
   
    esDhcp6CIfAcquiredIaT1 OBJECT-TYPE
        SYNTAX          Unsigned32
        MAX-ACCESS      read-only
        STATUS          current
        DESCRIPTION
            "The T1 timer of the acquired IA."             
        ::= { esDhcp6CIfAcquiredIaEntry 7 }

    esDhcp6CIfAcquiredIaT2 OBJECT-TYPE
        SYNTAX          Unsigned32
        MAX-ACCESS      read-only
        STATUS          current
        DESCRIPTION
            "The T2 timer of the acquired IA."  
        ::= { esDhcp6CIfAcquiredIaEntry 8 }
 
    esDhcp6CIfAcquiredIaExpireTime OBJECT-TYPE        
        SYNTAX          Unsigned32
        MAX-ACCESS      read-only
        STATUS          current
        DESCRIPTION
            "The expire time of acquired IA."            
        ::= { esDhcp6CIfAcquiredIaEntry 9 }
               
-- -----------------------------------------------------------------------------
    esDhcp6CIfAddrTable OBJECT-TYPE
        SYNTAX          SEQUENCE OF EsDhcp6CIfAddrEntry
        MAX-ACCESS      not-accessible
        STATUS          current
        DESCRIPTION
             "The table contains per-interface DHCPv6 address acquired from DHCPv6
             server."
        ::= { esDhcp6ClientStatusObjects 3 }

    esDhcp6CIfAddrEntry OBJECT-TYPE
        SYNTAX          EsDhcp6CIfAddrEntry
        MAX-ACCESS      not-accessible
        STATUS          current
        DESCRIPTION
            "Defines an entry in the esDhcp6CIfAddrTable."
        INDEX  { 
            esDhcp6CIfAcquiredIaId,
            esDhcp6CIfAddrInetAddr
        }
        ::= { esDhcp6CIfAddrTable 1 }

    EsDhcp6CIfAddrEntry ::= SEQUENCE {           
            esDhcp6CIfAddrInetAddr           InetAddressIPv6,           
            esDhcp6CIfAddrPreferLifeTime     Unsigned32,
            esDhcp6CIfAddrValidLifeTime      Unsigned32,                  
            esDhcp6CIfAddrExpireTime         Unsigned32
    }

    esDhcp6CIfAddrInetAddr OBJECT-TYPE
        SYNTAX         InetAddressIPv6
        MAX-ACCESS     not-accessible
        STATUS         current
        DESCRIPTION
            "The acquired address from DHCPv6 server."            
        ::= { esDhcp6CIfAddrEntry 1 }
   
    esDhcp6CIfAddrPreferLifeTime OBJECT-TYPE
        SYNTAX          Unsigned32
        MAX-ACCESS      read-only
        STATUS          current
        DESCRIPTION
            "The prefer lifetime of the acquired address."             
        ::= { esDhcp6CIfAddrEntry 2 }
      
    esDhcp6CIfAddrValidLifeTime OBJECT-TYPE
        SYNTAX      Unsigned32
        MAX-ACCESS  read-only
        STATUS      current
        DESCRIPTION
            "The valid lifetime of the acquired address."
        ::= { esDhcp6CIfAddrEntry 3 } 
                          
    esDhcp6CIfAddrExpireTime OBJECT-TYPE
        SYNTAX      Unsigned32
        MAX-ACCESS  read-only
        STATUS      current
        DESCRIPTION
            "The expire time of the acquired address."           
        ::= { esDhcp6CIfAddrEntry 4 }  
  
-- -----------------------------------------------------------------------------
    esDhcp6CIfPrefixTable OBJECT-TYPE
        SYNTAX          SEQUENCE OF EsDhcp6CIfPrefixEntry
        MAX-ACCESS      not-accessible
        STATUS          current
        DESCRIPTION
             "The table contains all acquired prefixes from DHCPv6 server(s)."
        ::= { esDhcp6ClientStatusObjects 4 }

    esDhcp6CIfPrefixEntry OBJECT-TYPE
        SYNTAX          EsDhcp6CIfPrefixEntry
        MAX-ACCESS      not-accessible
        STATUS          current
        DESCRIPTION
            "Defines an entry in the esDhcp6CIfPrefixTable."
        INDEX  { 
              esDhcp6CIfAcquiredIaId,
              esDhcp6CIfPrefixAddr,
              esDhcp6CIfPrefixAddrLen }
        ::= { esDhcp6CIfPrefixTable 1 }

    EsDhcp6CIfPrefixEntry ::= SEQUENCE {          
            esDhcp6CIfPrefixAddr             InetAddressIPv6,
            esDhcp6CIfPrefixAddrLen          InetAddressPrefixLength,
            esDhcp6CIfPrefixPreferLifeTime   Unsigned32,
            esDhcp6CIfPrefixValidLifeTime    Unsigned32,                  
            esDhcp6CIfPrefixExpireTime       Unsigned32
        }
    
    esDhcp6CIfPrefixAddr OBJECT-TYPE
        SYNTAX          InetAddressIPv6
        MAX-ACCESS      not-accessible
        STATUS          current
        DESCRIPTION
            "The address of the acquired prefix."
        ::= { esDhcp6CIfPrefixEntry 1 }

    esDhcp6CIfPrefixAddrLen OBJECT-TYPE
        SYNTAX          InetAddressPrefixLength
        MAX-ACCESS      not-accessible
        STATUS          current
        DESCRIPTION
            "The prefix length of the acquired prefix."
           
        ::= { esDhcp6CIfPrefixEntry 2 }
        
    esDhcp6CIfPrefixPreferLifeTime OBJECT-TYPE
        SYNTAX          Unsigned32
        MAX-ACCESS      read-only
        STATUS          current
        DESCRIPTION
            "The prefer lifetime of the acquired prefix."             
        ::= { esDhcp6CIfPrefixEntry 3 }

    esDhcp6CIfPrefixValidLifeTime OBJECT-TYPE
        SYNTAX      Unsigned32
        MAX-ACCESS  read-only
        STATUS      current
        DESCRIPTION
            "The valid lifetime of the acquired prefix."             
        ::= { esDhcp6CIfPrefixEntry 4 }

    esDhcp6CIfPrefixExpireTime OBJECT-TYPE
        SYNTAX      Unsigned32
        MAX-ACCESS  read-only
        STATUS      current
        DESCRIPTION
            "The expire time of the acquired prefix"
        ::= { esDhcp6CIfPrefixEntry 5 }
        
--  ***************************************************************************	
--  Conformance
--  ***************************************************************************
    esDhcp6ClientCompliances OBJECT IDENTIFIER ::= { esDhcp6ClientConformance 1 }
		
	esDhcp6ClientCompliance MODULE-COMPLIANCE
		STATUS          current
		DESCRIPTION 
			"The compliance statement for entities which implement the 
			DLINKES-DHCP6-CLIENT-MIB."
		MODULE -- this module
		MANDATORY-GROUPS { 
		    esDhcp6CBasicGroup,
		    esDhcp6CBasicStatusGroup
		}	
		
		OBJECT esDhcp6CIfMinRefresh
        MIN-ACCESS      read-only
        DESCRIPTION
            "It is complaint to support read only if the implementation doesn't
            support setting acceptable information refresh time."
        
        OBJECT esDhcp6CIfAcqAddrRapidCommit
        MIN-ACCESS      read-only
        DESCRIPTION
            "It is complaint to support read only if the implementation doesn't
            support rapid-commit for acquiring address."  
                     
		GROUP       esDhcp6CPrefixDelegationGroup
        DESCRIPTION
              "This group is required only if the agent supports requesting
              for prefix delegation through a specified interface."
                
		GROUP       esDhcp6CPrefixDelegStatusGroup
        DESCRIPTION
              "This group is required only if the agent supports requesting
              for prefix delegation through a specified interface."
        
        OBJECT esDhcp6CIfPdCfgRapidCommit
        MIN-ACCESS      read-only
        DESCRIPTION
            "It is complaint to support read only if the implementation doesn't
            support rapid-commit for requesting the prefix delegation."
                        
	    ::= { esDhcp6ClientCompliances 1 }
		
	esDhcp6ClientGroups OBJECT IDENTIFIER ::= { esDhcp6ClientCompliances 2 }
		
    esDhcp6CBasicGroup OBJECT-GROUP
		OBJECTS { 
		    esDhcp6ClientDuid, 
		    dhcp6ClientRestartIf, 
		    esDhcp6CIfAcquireAddrEnabled, 
		    esDhcp6CIfAcqAddrRapidCommit, 
		    esDhcp6CIfMinRefresh, 
			esDhcp6CIfRowStatus 
		}
		STATUS current
		DESCRIPTION 
			"This group contains the collection of objects related to  
			acquiring IPv6 address on an interface from DHCPv6 server."						
		::= { esDhcp6ClientGroups 1 }

		
	esDhcp6CBasicStatusGroup OBJECT-GROUP
		OBJECTS { 
		    esDhcp6CIfStateCode, 
		    esDhcp6CIfStatusEventExpire, 		   
		    esDhcp6CIfAcquiredIaServerAddr, 
		    esDhcp6CIfAcquiredIaServerDUID, 
		    esDhcp6CIfAcquiredIaServerPref, 
		    esDhcp6CIfAcquiredIaT1, 
		    esDhcp6CIfAcquiredIaT2, 
			esDhcp6CIfAcquiredIaExpireTime, 
			esDhcp6CIfAddrPreferLifeTime, 
			esDhcp6CIfAddrValidLifeTime, 
			esDhcp6CIfAddrExpireTime
		}
		STATUS current
		DESCRIPTION 
			"This group contains the collection of objects about the status 
			of acquired IPv6 address and the information about DHCPv6 server."
		::= { esDhcp6ClientGroups 2 }

		
	esDhcp6CPrefixDelegationGroup OBJECT-GROUP
		OBJECTS { 
		    esDhcp6CIfPdCfgPrefixName, 
		    esDhcp6CIfPdCfgHintAddr, 
		    esDhcp6CIfPdCfgHintLen, 
		    esDhcp6CIfPdCfgRapidCommit, 
		    esDhcp6CIfPdCfgRowStatus
		}
		STATUS current
		DESCRIPTION 
			"This group contains the collection of objects related to  
			acquiring IPv6 prefix on an interface from DHCPv6 server."
		::= { esDhcp6ClientGroups 3 }
		
	esDhcp6CPrefixDelegStatusGroup OBJECT-GROUP
		OBJECTS { 		 
		    esDhcp6CIfPrefixPreferLifeTime, 
		    esDhcp6CIfPrefixValidLifeTime, 
		    esDhcp6CIfPrefixExpireTime
		}
		STATUS current
		DESCRIPTION 
			"This group contains the collection of objects about the status 
			of the acquired prefixes."
		::= { esDhcp6ClientGroups 4 }

END
